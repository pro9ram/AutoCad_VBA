Attribute VB_Name = "ClsAptInfo"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Const VK_ESCAPE = &H1B, VK_ENTER = &HD, VK_LBUTTON = &H1

Private mtxObj As Object 'AcadText
Private plObj As Object 'AcadLWPolyline
    
Private odinfo As ClsODInfo

Private mtxt As String

Private startHo As Integer
Private endHo As Integer
Private floor As Integer

Private curHo As Integer

Private amap As AutocadMAP.AcadMap


Private apttblname As String

Private filterlayr() As String



Function load()

    Dim layername As String
    Dim mt As AcadText
    Dim bret As Boolean
    Dim newho As Integer
    
    Set amap = ThisDrawing.Application.GetInterfaceObject("AutoCADMap.Application")
    
    filterlayr() = Split(FLT_APT_LAYER, ",")
    
    apttblname = "층호수정보"
    
    Set mtxObj = Nothing
    Do While (mtxObj Is Nothing)
    
        With ThisDrawing
            On Error Resume Next
            Set mtxObj = selectRepeatEntity()
            
            If TypeOf mtxObj Is AcadText Then
                Set mt = mtxObj
            Else
                Set mtxObj = Nothing
            End If
        End With
    Loop
    
    
    mtxt = mt.textString
    
    'ThisDrawing.Utility.prompt "" & mtxt & vbLf
    checkFloor
    
    newho = ThisDrawing.Utility.GetInteger
    
    If newho <> 0 Then
        endHo = endHo + (newho - startHo)
        startHo = newho
        
        ThisDrawing.Utility.prompt "층: " & floor & ", 호: " & startHo & "~" & endHo & vbLf
        curHo = startHo
    End If
    
    Set plObj = Nothing
    
    
    bret = createAptODBTable(apttblname)  '테이블 생성
    
    Do While (plObj Is Nothing And bret = True)
        With ThisDrawing
        On Error Resume Next
        
            'ThisDrawing.SendCommand "(setvar ""cmdecho"" 0)" & vbCr
            Dim ss As New clsSelSets
            Set plObj = ss.selectOnePolyline
                
            'Set plObj = selectRepeatEntity()
            
            If plObj Is Nothing Then
                Exit Do
            End If
            
            layername = plObj.layer
            
            
            If TypeOf plObj Is AcadLWPolyline And isValidLayer(layername) Then
                
                ThisDrawing.SendCommand "(setq av_sel2 (ssget ""P""))" & vbCr
                'ThisDrawing.SendCommand "(Setq av_sel2 (ssget '((0 . ""LWPOLYLINE"")(8 . ""0""))))" & vbCr
                ThisDrawing.SendCommand "(setq index 0)" & vbCr
                ThisDrawing.SendCommand "(setq av_ssn (ssname av_sel2 index))" & vbCr
                ThisDrawing.SendCommand "(setq av_vl_ssn (vlax-ename->vla-object av_ssn))" & vbCr
                ThisDrawing.SendCommand "(ade_odaddrecord av_ssn """ & apttblname & """)" & vbCr
                'ThisDrawing.SendCommand "(ade_odsetfield av_ssn "호수정보" "호수"  0 av_val)"
                
                'Dim ssetObj As AcadSelectionSet
                'Set ssetObj = ThisDrawing.ActiveSelectionSet
        
                'ssetObj.Select acSelectionSetLast
                
                'ThisDrawing.SendCommand "(setvar ""cmdecho"" 1)" & vbCr
                
                'Set plObj = ssetObj.Item(0)
                 
                'Set plObj = selectRepeatEntity()
                
                addInfoToOD curHo
                
                plObj.color = acMagenta
                ThisDrawing.Utility.prompt "호: " & curHo & ",층: " & floor & vbLf
                
                curHo = curHo + 1
                
                Set plObj = Nothing
            Else
                Set plObj = Nothing
            End If
        
        End With
        
    Loop
    
End Function


Function loadEx()

    Dim TArr() As String
    Dim layername As String
    Dim mt As AcadText
    Dim bret As Boolean
    Dim newho As Integer
    Dim m1 As Double
    Dim m2 As Double
    Dim plObjs() As AcadEntity
    Dim ent As Variant
    Dim idx As Integer
    
    Set amap = ThisDrawing.Application.GetInterfaceObject("AutoCADMap.Application")
    
    filterlayr() = Split(FLT_APT_LAYER, ",")
    
    apttblname = "아파트평폴리곤"
    
    Set mtxObj = Nothing
    Do While (mtxObj Is Nothing)
    
        With ThisDrawing
            On Error Resume Next
            Set mtxObj = selectRepeatEntity()
            
            If TypeOf mtxObj Is AcadText Then
                Set mt = mtxObj
            Else
                Set mtxObj = Nothing
            End If
        End With
    Loop
    
    
    mtxt = Trim(mt.textString)
    idx = 0
    
    bret = createAptPyODBTable(apttblname)  '테이블 생성
            
    plObjs = selectPLObjs
    
    
    For Each ent In plObjs
        
        Set plObj = ent
    
        layername = plObj.layer
        
        If TypeOf plObj Is AcadLWPolyline And isValidLayer(layername) Then
            
            ThisDrawing.SendCommand "(setq av_sel2 (ssget ""P""))" & vbCr
            ThisDrawing.SendCommand "(setq index " & idx & ")" & vbCr
            ThisDrawing.SendCommand "(setq av_ssn (ssname av_sel2 index))" & vbCr
            ThisDrawing.SendCommand "(setq av_vl_ssn (vlax-ename->vla-object av_ssn))" & vbCr
            ThisDrawing.SendCommand "(ade_odaddrecord av_ssn """ & apttblname & """)" & vbCr
            
            
            TArr() = Split(mtxt, "/")
            size = UBound(TArr)
            
            If size = 1 Then
            
                m1 = CDbl(Trim(TArr(0)))
                m2 = CDbl(Trim(TArr(1)))
            
                If addPyInfoToOD(m1, m2) = True Then
           
                    plObj.color = acMagenta
                    ThisDrawing.Utility.prompt "공급: " & m1 & ",전용: " & m2 & vbLf
                Else
                    ThisDrawing.Utility.prompt "오류! 공급: " & m1 & ",전용: " & m2 & vbLf
                End If
            End If
            
        End If
        
        idx = idx + 1
        
    Next
    
    
End Function



Private Function isValidLayer(layername As String) As Boolean

    Dim str As Variant

    For Each str In filterlayr
    
        If layername = str Then
        
            isValidLayer = True
            Exit Function
        End If
       
    Next

    isValidLayer = False

End Function


Private Function addPyInfoToOD(m1 As Double, m2 As Double) As Boolean

    Dim col As New Collection


    Set odinfo = New ClsODInfo
    
    odinfo.init plObj, apttblname
    'odinfo.setFieldDefs createAptODFielDefs
    odinfo.setTableInstance
     
    col.add m1
    col.add m2
    
    addPyInfoToOD = odinfo.setInfo(col)

End Function



Private Function addInfoToOD(ho As Integer)

    Dim col As New Collection
    
    Set odinfo = New ClsODInfo

    odinfo.init plObj, apttblname
    'odinfo.setFieldDefs createAptODFielDefs
    odinfo.setTableInstance
     
    col.add floor
    col.add ho
    
    odinfo.setInfo col

End Function


Private Function createAptODFielDefs() As ODFieldDefs

    Dim ODfdfs As ODFieldDefs
    Dim ODfdf As ODFieldDef

    Set ODfdfs = amap.Projects(ThisDrawing).MapUtil.NewODFieldDefs
    
    Set ODfdf = ODfdfs.add("층수", "아파트 층수", 0, 0)
    Set ODfdf = ODfdfs.add("호수", "아파트 호수", 0, 1)
    
    Set createAptODFielDefs = ODfdfs
    
End Function



Private Function selectRepeatEntity() As AcadObject
    Dim str As Object
    Dim returnObj1 As AcadObject
    Dim basePnt1 As Variant
  
    Set returnObj1 = Nothing
    
    With ThisDrawing
        On Error Resume Next
        ThisDrawing.Utility.getEntity returnObj1, basePnt1, "Get Text Object: "
    
    End With
    
    Debug.Print Err.Description
 
    
    If Err.Description = "Method 'GetEntity' of object 'IAcadUtility' failed" Then
    
        If CheckKey(VK_ESCAPE) = True Or CheckKey(VK_ENTER) Then
            Debug.Print "End"
            End
        Else
            Debug.Print "Resume"
            Resume
        End If
    ElseIf Err.Description = "Key not found" Then
    
    
    End If
    
    Set selectRepeatEntity = returnObj1

End Function
 


Private Function checkFloor()

    Dim TArr() As String
    Dim size As Integer
    Dim flen As Integer
    Dim itmp As Integer
    
    TArr() = Split(mtxt, "-")
    size = UBound(TArr)
    
    
    If size = 2 Then
    
        startHo = CInt(Trim(TArr(0)))
        
        flen = Len(TArr(1))
        floor = CInt(Trim(Left(TArr(1), flen - 1)))
        endHo = CInt(Trim(TArr(2)))
     
    ElseIf size = 1 Then
    
        If EndsWith(TArr(0), "F") = True Then
            
            flen = Len(TArr(0))
            floor = CInt(Trim(Left(TArr(0), flen - 1)))
            
            'floor = CInt(Trim(TArr(0)))
            endHo = CInt(Trim(TArr(1)))
            
            startHo = endHo
             
        End If
        
        If EndsWith(TArr(1), "F") = True Then
            startHo = CInt(Trim(TArr(0)))
            
            flen = Len(TArr(1))
            floor = CInt(Trim(Left(TArr(1), flen - 1)))
            
            'floor = CInt(Trim(TArr(1)))
            endHo = startHo
        End If
    End If
    
    If endHo < startHo Then
    
        itmp = startHo
        startHo = endHo
        endHo = itmp
    
    End If
    
    
    curHo = startHo
    
    ThisDrawing.Utility.prompt "층: " & floor & ", 호:" & startHo & "~" & endHo & vbLf
    

End Function

Attribute VB_Name = "ClsAreaChecker"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False


Function load()

    Dim ents() As AcadEntity
        
    Dim ent1 As AcadEntity
    Dim plroad() As AcadEntity
    
    Dim reg1 As AcadRegion
    Dim reg2 As AcadRegion
    Dim idx As Integer
    Dim area As Double
    Dim marea As Double
    
    idx = 0
    area = 0
    marea = 0
    
    
    plroad = selectPolylineObs
    
    ttt = ThisDrawing.ModelSpace.AddRegion(plroad)
    
    
    For i = 0 To UBound(ttt)

        Set reg2 = ttt(i)
         
        
        If reg2.area > marea Then
            marea = reg2.area
            idx = i
        End If
    Next i
    
    Set reg1 = ttt(idx)
    
    For i = 0 To UBound(ttt)
    
        If i <> idx Then
            Set reg2 = ttt(i)
            
            Debug.Print reg2.ObjectName
            
            
            reg1.Boolean acSubtraction, reg2
        End If
        
    Next i
     
    'expoldeRegionEx reg1, acRed
    

End Function

Attribute VB_Name = "ClsBoundary"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private baseents() As AcadEntity
Private dstents() As AcadEntity

Private baseregs As Variant
Private dstregs As Variant


Private dstcount As Integer
Private idx As Integer


Private regs As Variant








Public Function selects()

    Dim conv As New ClsConverter
    Dim reg As AcadRegion
    Dim reg2 As AcadRegion
    Dim lyrname As String
    Dim dstent As Variant
    Dim result As Boolean
    
    idx = 0
    
    

    baseents = selectPLObjs
    dstents = selectPLObjs
    
    If IsArrayEmpty(baseents) = False And IsArrayEmpty(dstents) = False Then
        
        dstcount = UBound(dstents)
        
        
        For k = 0 To UBound(dstents)
        
            ReDim dstent(0 To 0) As AcadEntity
            Set dstent(0) = dstents(k)              '한개씩 처리
 
            lyrname = dstents(k).layer               '현재레이어 설정
        
            dstregs = ThisDrawing.ModelSpace.AddRegion(dstent)
            
            result = False
            
            For i = 0 To UBound(dstregs)            '하나씩 처리하니 region도 하나겠지?
            
                
                Set reg = dstregs(i)
                
                baseregs = ThisDrawing.ModelSpace.AddRegion(baseents)       'base 도로는 subtract로 잘리기때문에 매번 생성함
                
                For j = 0 To UBound(baseregs)
                    Set reg2 = baseregs(j)
                    reg.Boolean acSubtraction, reg2
                Next j
                
                If reg.area > 0 Then
                    result = expoldeRegion(reg, lyrname)
                    
          
                    If result = True Then
                        dstent(0).Delete        '올바르게 처리되었을때만 원본을 삭제함
                    Else
                        reg.Delete
                    End If
                End If
                
            Next i
            
                      
        
        Next k
        
    End If
    
    
    'explodeRegions
    
    Debug.Print ""
    'reg2.Boolean acSubtraction, reg3
    
    
    
    'expoldeRegion reg2
    
    'expoldeRegion reg1
     

End Function

 




Private Function expoldeRegion(reg As Variant, lyrname As String) As Boolean

    Dim has As Boolean
    Dim conv As New ClsConverter
    Dim Punto As Variant
    Dim ent As AcadLWPolyline
    Dim ret As Boolean
    Dim arr As Variant
    Dim subreg As Variant

    ret = False
    
    has = hasSubRegion(reg)
    
    If has = True Then
    
        arr = reg.Explode
        size = UBound(arr)
        
        For i = 0 To size
            
            Set subreg = arr(i)
            
            has = hasArc(subreg)
        
            If has = False Then
            
                Set ent = conv.reg2polyline(subreg)
                ent.layer = lyrname
                subreg.Delete
                ret = True
            End If
        
        Next i
        
        reg.Delete
    
    
    Else
    
        has = hasArc(reg)
        
        If has = False Then
        
            Set ent = conv.reg2polyline(reg)
            ent.layer = lyrname
            reg.Delete
            ret = True
        End If
    End If
    

    expoldeRegion = ret

End Function



Private Function IsArrayEmpty(anArray As Variant) As Boolean

    Dim ret As Boolean
    
    ret = True

    On Error GoTo IS_EMPTY
    If (UBound(anArray) >= 0) Then
    
        ret = False
    
    End If
IS_EMPTY:
        IsArrayEmpty = ret
End Function

Private Function hasSubRegion(reg As Variant) As Boolean

    Dim arr As Variant
    Dim size As Integer
    Dim ret As Boolean

    ret = False

    arr = reg.Explode
    size = UBound(arr)
    
    If size > 0 Then
        If TypeOf arr(0) Is AcadRegion Then
            ret = True
        
        End If
    End If
    
    
    For i = 0 To size
        arr(i).Delete
    
    Next
    
    hasSubRegion = ret

End Function


Private Function hasArc(reg As Variant) As Boolean

    Dim arr As Variant
    Dim size As Integer
    Dim ret As Boolean

    ret = False

    arr = reg.Explode
    size = UBound(arr)
    
    For i = 0 To size
        If TypeOf arr(i) Is AcadArc Then
            arr(i).color = acBlue
            ret = True
            Exit For
        End If
    
    Next
    
    For i = 0 To size
        arr(i).Delete
    
    Next
    
    hasArc = ret

End Function

Attribute VB_Name = "ClsBreaker"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private ptd1() As Double
Private ent As AcadEntity
Private ptd2() As Double
Private ptdn1() As Double
Private ptdn2() As Double


Private pt1 As New clsPoint
Private pt2 As New clsPoint

Function init()
    Dim ss As New clsSelSets
    
    On Error GoTo EndOfFunction
    Debug.Print "==================START ================="
    
    
    Set ent = ss.selectOnePolyline
    
    If ent Is Nothing Then
        ThisDrawing.Utility.prompt "선택 오류가 발생했습니다. 하나만 선택해주세요"
        GoTo EndOfFunction
    End If

EndOfFunction:
    
    Debug.Print "DONE"
    
End Function


Function setBaseEntity(e As AcadEntity)

    Set ent = e

End Function


Function load()
    
    Dim pr As New clsPolygonReader
    
    Dim ddd() As Double
  

    ThisDrawing.SetVariable "osmode", 543
    ptd1 = ThisDrawing.Utility.getPoint(, "Enter a point1: ")
    ptd2 = ThisDrawing.Utility.getPoint(, "Enter a point2: ")
    
    Set ent = ent.Copy
    
    
 
    
    Debug.Print "ptd1(0) = " & ptd1(0)
    Debug.Print "ptd1(1) = " & ptd1(1)
    Debug.Print "ptd2(0) = " & ptd2(0)
    Debug.Print "ptd2(1) = " & ptd2(1)
    
    
    'addDonutA ptd1(0), ptd1(1)
    'addDonutA ptd2(0), ptd2(1)
    
    ptdn1 = addVertex(ent, ptd1(0), ptd1(1))
    ptdn2 = addVertex(ent, ptd2(0), ptd2(1))
    
    If ptdn1(0) = 0 Or ptdn1(1) = 0 Or ptdn2(0) = 0 Or ptdn2(1) = 0 Then
        ent.Delete
        ThisDrawing.Utility.prompt "포인트 선택 오류가 발생했습니다."
        GoTo EndOfFunction
    End If
    
    pt1.initPt ptdn1
    pt2.initPt ptdn2
    
  
    
    addDonut pt1.x, pt1.y
    addDonut pt2.x, pt2.y
    
    pr.init ent
    pr.setIndexByPoint pt1
    pr.setEIndexByPoint pt2
    
    ddd = pr.getShortLine2()
    
    Set ret = ThisDrawing.ModelSpace.AddLightWeightPolyline(ddd)
    
    ent.Delete
    
EndOfFunction:
    
    Debug.Print "DONE"

    
End Function

Attribute VB_Name = "ClsBridge"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private ent As AcadEntity
Private polygon As New clsPolygonReader
Private sidx As Integer
Private eidx As Integer


'새 라인 정보
Private new1d() As Double
Private new2d() As Double

Private pts As New clsPoint
Private pte As New clsPoint


Private line As AcadLWPolyline
Private coords() As Double

Private tailLEN As Integer



Private layername As String




Function createBridge()


    Dim selec1 As New ClsSelEntity
    Dim selec2 As New ClsSelEntity
    Dim orgent As AcadEntity
    
    Dim pt1 As clsPoint
    Dim pt2 As clsPoint
    
    Dim p1() As Double
    Dim p2() As Double
    
    Dim temp As String
    
    tailLEN = 3
    
    selec1.selectPolyline ("Get Polyline 1: ")
    Set orgent = selec1.getEntity
    Set pt1 = selec1.getPoint

    selec2.selectPolyline ("Get Polyline 2: ")
    Set orgent = selec2.getEntity
    Set pt2 = selec2.getPoint
    
    Set ent = orgent.Copy
    
    
    new1d = addVertex2(ent, pt1.x, pt1.y)
    new2d = addVertex2(ent, pt2.x, pt2.y)
    
    pts.x = new1d(0)
    pts.y = new1d(1)
    
    pte.x = new2d(0)
    pte.y = new2d(1)
    
    
    polygon.init ent
    sidx = polygon.getIndexByPoint(pts)
    eidx = polygon.getIndexByPoint(pte)
    
    Set line = getShortLine
    
    p1 = addHead()
    line.addVertex 0, p1
    line.Update
    
    p2 = addTail()
    size = (UBound(line.Coordinates) + 1) / 2
    
    line.addVertex size, p2
    
    temp = getDefaultBridgeLayer
    
    layername = getAddLayerName(temp)
    line.layer = layername
    
    ent.Delete
    
    Debug.Print ""
    

End Function


Function getShortLine() As AcadLWPolyline

    Dim line1 As AcadLWPolyline
    Dim line2 As AcadLWPolyline
    
    polygon.setIndex sidx
    Set line1 = getLine1
    
    polygon.setIndex sidx
    polygon.setReverse
    Set line2 = getLine1
    
    
    len1 = getLWPDistance(line1)
    len2 = getLWPDistance(line2)
    
    
    If len1 < len2 Then
        'LINE 1
        line2.Delete
        polygon.setReverse
    Else
        'LINE 2
        line1.Delete
        Set line1 = line2
    End If
    
    Set getShortLine = line1
    
End Function

    
Public Function addHead() As Double()

    Dim ptx As New clsPoint
    Dim ptn As New clsPoint
    
    Dim p1(0 To 1) As Double
    
    polygon.setIndex sidx
    Set ptn = polygon.nextPoint
    
    ptx.x = pts.x + 5
    ptx.y = pts.y
    
    'addDonutA pts.x, pts.y
    'addDonutA ptn.x, ptn.y
    'addDonutA ptx.x, ptx.y
    
    ang = getAngleEx(pts.x, pts.y, ptx.x, ptx.y, ptn.x, ptn.y)
    
    
    ang = ang - PI * 5 / 4
    
    xx = pts.x + tailLEN * Math.Cos(ang)
    yy = pts.y + tailLEN * Math.Sin(ang)
    
    
    'addDonutA xx, yy
     
    p1(0) = xx
    p1(1) = yy
    
    addHead = p1 'line1.addVertex 0, p1
     

End Function


  
Public Function addTail() As Double()

    
    Dim ptx As New clsPoint
    Dim ptn As New clsPoint
    
    Dim p1(0 To 1) As Double
    
    
    coords = line.Coordinates
    size = UBound(coords)
    
    ptn.x = coords(size - 3)
    ptn.y = coords(size - 2)
    
    pte.x = coords(size - 1)
    pte.y = coords(size)
    
    ptx.x = ptn.x + 5
    ptx.y = ptn.y
    
    'addDonutA pte.x, pte.y
    'addDonutA ptn.x, ptn.y
    'addDonutA ptx.x, ptx.y
    
    ang = getAngleEx(ptn.x, ptn.y, ptx.x, ptx.y, pte.x, pte.y)
    
    
    ang = ang + PI * 1 / 4
    
    xx = pte.x + tailLEN * Math.Cos(ang)
    yy = pte.y + tailLEN * Math.Sin(ang)
    
    
    'addDonutA xx, yy
     
    p1(0) = xx
    p1(1) = yy
    
    addTail = p1 'line1.addVertex 0, p1
     

End Function


Function getLine1() As AcadLWPolyline

    Dim pline As AcadLWPolyline
    Dim ptc As New clsPoint
    Dim pt As New clsPoint
    Dim ddd() As Double
    Dim size As Integer
    Dim eidx2 As Integer
    
    eidx2 = 0
    size = polygon.getSize
    
    
    Set ptc = polygon.getPoint(sidx)
    'addDonutA ptc.x, ptc.y
        
    For idx = 0 To size
        Set pt = polygon.nextPoint
        
        'addDonutA pt.x, pt.y
        
        If pte.isEquals(pt) = True Then
            eidx2 = idx + 1
            Exit For
        End If
        
    Next
    
    ReDim ddd(0 To eidx2 * 2 + 1) As Double
        
    ddd(0) = ptc.x
    ddd(1) = ptc.y
    
    
    polygon.setIndex sidx
        
    For idx = 1 To eidx2
        Set pt = polygon.nextPoint
        ddd(idx * 2) = pt.x
        ddd(idx * 2 + 1) = pt.y
    Next
    
    Set getLine1 = ThisDrawing.ModelSpace.AddLightWeightPolyline(ddd)
    
    
    
End Function

Public Function getLWPDistance(ent As AcadLWPolyline) As Double


    Dim ddd() As Double
    Dim size As Integer
    Dim x1, y1, x2, y2 As Double
    Dim sum As Double
    
    sum = 0
    ddd = ent.Coordinates
    
    size = UBound(ddd)
    
    
    x1 = ddd(0)
    y1 = ddd(1)
    
    For i = 2 To size Step 2
    
        x2 = ddd(i)
        y2 = ddd(i + 1)
        
        sum = sum + getDistance(x1, y1, x2, y2)
        
        x1 = x2
        y1 = y2
    
    
    Next

    getLWPDistance = sum


End Function



Public Function setCoords()

    coords = line.Coordinates
    

End Function

Attribute VB_Name = "ClsChamfer"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private orgLayer As String
Private oldroad As AcadEntity
Private newroad As AcadEntity
Private fillet As AcadEntity

Private ptIntersection As Variant

Private isEdited As Boolean


Public Function load()

    Dim pt1 As New clsPoint
    Dim pt3 As New clsPoint
    Dim retLine As AcadLine
    Dim tmp As Variant
    
    Dim sp(0 To 2) As Double
    Dim ep(0 To 2) As Double
    
    Dim np1 As New clsPoint
    Dim np2 As New clsPoint
    Dim np3 As New clsPoint
     
    Dim pr As New clsPolygonReader
    
    Dim newroadsplit() As Double
    Dim oldroadsplit() As Double
    Dim additionsplit(0 To 3) As Double
    
    Dim merge As New ClsMerger
    Dim resultd() As Double
    Dim result As AcadEntity
    Dim test As Boolean
    
    
    Dim selec1 As New ClsSelEntity
    Dim selec2 As New ClsSelEntity
    Dim undoPoint As AcadEntity
    
    Dim seler As New ClsSelReal
    Dim frad As Double
    
    Dim selecs As New clsSelSets
    
    Dim okcnt As Integer
    Dim ok As Boolean
    
    isEdited = False
    okcnt = 0
    
    ok = selec1.selectPolyline("#Get Polyline 1: ")
    Set newroad = selec1.getEntity
    Set pt1 = selec1.getPoint
    
    If ok = False Then
        ThisDrawing.Utility.prompt "선택에 오류가 발생했습니다."
        GoTo EndOfFunction
    
    End If
    
    Set undoPoint = ThisDrawing.ModelSpace.AddText("UU-U", selec1.getMovePoindD(5), 2)
    
    ok = selec2.selectPolyline("#Get Polyline 2: ")
    Set oldroad = selec2.getEntity
    Set pt3 = selec2.getPoint
    
        
    If ok = False Then
        ThisDrawing.Utility.prompt "선택에 오류가 발생했습니다."
        GoTo EndOfFunction
    
    End If
    
    
    isEdited = hasProperties(newroad)
    
    
    ptIntersection = searchCrossVertext(newroad, oldroad)
    
    For i = 0 To UBound(ptIntersection) Step 3
        'addDonutA ptIntersection(i), ptIntersection(i + 1)          '!!!!!!!!!!!!!!!!!!!!!!
        
        ok = isContains(newroad, CDbl(ptIntersection(i)), CDbl(ptIntersection(i + 1)))
        If ok = True Then
            okcnt = okcnt + 1
        End If
    Next i
    
    
    If okcnt < 2 Then
        ThisDrawing.Utility.prompt "인접부분 확인바랍니다 - 접점: " & okcnt
        GoTo EndOfFunction
    
    End If
    
    
    sp(0) = pt1.x
    sp(1) = pt1.y
    ep(0) = pt3.x
    ep(1) = pt3.y
    
    Set retLine = ThisDrawing.ModelSpace.addLine(sp, ep)
    
    Debug.Print "chamfer created"
    
    newp1 = findVertexAtLine2(newroad, retLine, pt1)   '아크와 도로(새도로)의 접점 추가
    newp2 = findVertexAtLine2(oldroad, retLine, pt3)   '아크와 도로(구도로)의 접점 추가
   
   
    np1.initXy newp1(0), newp1(1)
    np2.initXy newp2(0), newp2(1)
    
    
    Debug.Print "np1: " & np1.x & ", " & np1.y
    Debug.Print "np2: " & np2.x & ", " & np2.y
    

    additionsplit(0) = np1.x
    additionsplit(1) = np1.y
    additionsplit(2) = np2.x
    additionsplit(3) = np2.y
   
    Set np3 = getFarPoint2Ex(newroad, ptIntersection, np1)     '기존도로 아크 접점에서 먼 지점을 찾는다
    
    
    addVertex oldroad, np3.x, np3.y     '기존도로에 접점추가
    

   
    Debug.Print "cross point created"
    
    pr.init newroad
    pr.setIndexByPoint np1
    pr.checkDirection pt3
    
    'addDonut5 np3.x, np3.y
    'addDonut5 np1.x, np1.y
    Debug.Print "newroad direction processed"
    
    sidx = pr.setIndexByPoint(np1)
    eidx = pr.setEIndexByPoint(np3)
    
    newroadsplit = pr.getLongLine2()
    'newroadsplit = pr.splitInnerLine(np3, np1)
    'addLine newroadsplit
    
    Debug.Print "newroad split created"
   
    pr.init oldroad
    pr.setIndexByPoint np2
    pr.checkDirection pt1
    
    Debug.Print "oldroad direction processed"
    
    sidx = pr.setIndexByPoint(np2)
    eidx = pr.setEIndexByPoint(np3)
    
    oldroadsplit = pr.getShortLine2()
    'oldroadsplit = pr.splitInnerLine(np2, np3)
    'addLine oldroadsplit
    
    
    
    Debug.Print "oldroad split created"
        
    size1 = UBound(newroadsplit)
    size2 = UBound(additionsplit)
    size3 = UBound(oldroadsplit)
    
    merge.setSize size1 + size2 + size3 + 2
    
    
    merge.add newroadsplit
    merge.add additionsplit
    merge.add oldroadsplit
    
    
    Set result = addLine(merge.getMerged)
    result.Closed = True
    'newroad.Delete
    retLine.Delete
    
    'ThisDrawing.SendCommand "sob" & vbCr
    
    orgLayer = newroad.layer
    result.layer = getAddLayerName(orgLayer)
    newroad.layer = getDelLayerName(orgLayer)
    
    If (orgLayer Like LYR_ADD & "*") Or isEdited = False Then
        newroad.Delete
    End If
    
EndOfFunction:
    If undoPoint Is Nothing = False Then
        undoPoint.Delete
    End If
    Debug.Print "DONE"
    
End Function

Attribute VB_Name = "ClsConverter"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private arr As Variant 'AcadLine of array
Private chk() As Boolean
Private size As Integer




Public Function reg2polyline(reg As Variant) As AcadLWPolyline


    Dim repeat As Boolean
    Dim ret() As Double
    Dim ret2() As Double
    Dim idx As Integer
    Dim line As AcadLine
    Dim retent As AcadLWPolyline
    
    repeat = True
    idx = 0
    
    
    arr = reg.Explode
    size = UBound(arr)
    
    
    
    ReDim chk(size) As Boolean
    ReDim ret(size * 2 + 1) As Double
        
    
    Set line = arr(i)
    vpt = line.startPoint
    
    chk(0) = True
    ret(0) = vpt(0)
    ret(1) = vpt(1)
    
    idx = idx + 2
    
    Do While repeat
    
        vpt = nextPoint(CDbl(vpt(0)), CDbl(vpt(1)))
        
        If vpt(0) = 0 And vpt(1) = 0 Then
            repeat = False
        Else
            ret(idx) = vpt(0)
            ret(idx + 1) = vpt(1)
            
            idx = idx + 2
        End If
    
    Loop
    
    ' 3D -> 2D
    idx = 0
    For i = 0 To UBound(ret)
    
        If ret(i) = 0 Then
            Exit For
        End If
    
        idx = idx + 1
    
    Next i
    
    ReDim ret2(idx - 1) As Double
    
    For i = 0 To UBound(ret2)
    
        ret2(i) = ret(i)
    
    Next i
    
    
    Set retent = ThisDrawing.ModelSpace.AddLightWeightPolyline(ret2)
    If retent.Closed = False Then
        retent.Closed = True
    End If
    
    
    For i = 0 To size
    
        Set line = arr(i)
        line.Delete
    
    Next i
    
     
    Set reg2polyline = retent

    
End Function

Private Function nextPoint(dx As Double, dy As Double) As Double()

    Dim line As AcadLine
    Dim vpts As Variant
    Dim vpte As Variant
    Dim ret(0 To 2) As Double
    

    For i = 0 To size
        If chk(i) = False Then
        
            Set line = arr(i)
            vpts = line.startPoint
            vpte = line.endPoint
            
            If vpts(0) = dx And vpts(1) = dy Then
                
                ret(0) = vpte(0)
                ret(1) = vpte(1)
                
                chk(i) = True
                Exit For
            End If
            
            If vpte(0) = dx And vpte(1) = dy Then
                
                ret(0) = vpts(0)
                ret(1) = vpts(1)
                chk(i) = True
                Exit For
            End If
            
        End If
    
    Next
    
    
    nextPoint = ret


End Function

Attribute VB_Name = "ClsEdgeRounder"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private retd() As Double
Private layername As String

Public Function load()

    Dim ent As AcadLWPolyline
    Dim ents() As AcadEntity
    Dim col As New Collection
    
    Dim ddd() As Double
    Dim ss As New clsSelSets
    Dim cx As Double
    Dim cy As Double
    Dim x1 As Double
    Dim y1 As Double
    Dim x2 As Double
    Dim y2 As Double
    
    Dim angle As Double
    Dim retent As AcadLWPolyline
    Dim retpd() As Double
    Dim size As Integer
    Dim colidx As New Collection
    Dim colval As New Collection
    Dim offset As Integer
    Dim value As Double
    Dim width As Double
    Dim newrad As Double
    Dim temp As Variant
    
    ents = selectPLObjs
     
    
    For j = 0 To UBound(ents)
        
    
        Set ent = ents(j)
        
        ent.GetWidth 0, width, width
    
        'width = 4  'ent.GetWidth
        
        ddd = ent.Coordinates
        layername = ent.layer
        
        x1 = ddd(0)
        y1 = ddd(1)
        
        
        col.add x1
        col.add y1
        
        
        offset = 0
        size = UBound(ddd)
        
        For i = 2 To size - 2 Step 2
        
            offset = offset + 1
        
            cx = ddd(i)
            cy = ddd(i + 1)
            
            x2 = ddd(i + 2)
            y2 = ddd(i + 3)
            
            
            
            angle = getAngleEx(cx, cy, x1, y1, x2, y2)
        
            Debug.Print PI / 2 & "," & angle
        
            If isOrthogonalRadian(angle) = True Then
                
                retpd = getShortPoint(cx, cy, x1, y1, width)
                'addDonutA retpd(0), retpd(1)
                
                col.add retpd(0)
                col.add retpd(1)
                
                
                retpd = getShortPoint(cx, cy, x2, y2, width)
                'addDonutA retpd(0), retpd(1)
                
                col.add retpd(0)
                col.add retpd(1)
                
                colidx.add offset
                colval.add angle
                
                offset = offset + 1
            
            Else
                col.add cx
                col.add cy
            
            End If
        
            x1 = cx
            y1 = cy
            
            
        
        Next i
        
        
        col.add ddd(size - 1)
        col.add ddd(size)
        
        
        'ent.SetBulge 1, PI / 8
        'ent.Update
        'setWidth ent, 10, 10
        
        'ent.Explode
        
        'Debug.Print ""
    
    
        retd = toArray(col)
        
        Set retent = ThisDrawing.ModelSpace.AddLightWeightPolyline(retd)
        'retent.color = acBlue
        
        For i = 1 To colidx.count
            offset = colidx(i)
            value = colval(i)
            
             'Debug.Print PI & ">" & value
             
            If offset = 7 Then
                Debug.Print ">>"
            End If
            
            If (value > PI And value < 2 * PI) Or (value < 0 And value > -PI) Then
            
                newrad = PI / 8
            
                If value < 0 Then
                    value = Abs(value)
                Else
                    value = Abs(value - PI)
                    If value < PI_2 Then
                        value = PI - value
                    End If
                End If
                
                
                newrad = (PI - value) / 4
                
                Debug.Print offset & ">>> " & value & "(" & value / PI & ")" & ">>> " & PI / 8 & ">>> " & newrad
                retent.SetBulge offset, newrad
            Else
                newrad = -PI / 8
            
                If value < 0 Then
                    value = Abs(value + PI)
                Else
                    value = PI - value
                End If
            
                newrad = -value / 4
                Debug.Print offset & ">>> " & value & "(" & value / PI & ")" & ">>> " & -PI / 8 & ">>> " & newrad
                retent.SetBulge offset, newrad
            End If
            
            'If Abs(Abs(value - PI_2) - PI) < 0.0001 Then
            '    Debug.Print offset & ">>> " & value & ">>> "; PI / 8
            '    retent.SetBulge offset, PI / 8
            'Else
            '    Debug.Print offset & ">>> " & value & ">>> "; -PI / 8
            '    retent.SetBulge offset, -PI / 8
            'End If
            
        Next
        
        setWidth retent, width, width
        
        retent.Update
        retent.layer = ent.layer
        
        ent.Delete
        
        clearCollection col
        clearCollection colidx
        clearCollection colval
        
        
    Next j

End Function


Function toArray(col As Collection) As Double()
  Dim arr() As Double
  ReDim arr(0 To col.count - 1) As Double
  For i = 1 To col.count
      arr(i - 1) = col(i)
  Next
  toArray = arr
End Function


Function toIntArray(col As Collection) As Integer()
  Dim arr() As Integer
  ReDim arr(0 To col.count - 1) As Integer
  For i = 1 To col.count
      arr(i - 1) = col(i)
  Next
  toArray = arr
End Function


Function clearCollection(col As Collection)
     
        For k = 1 To col.count
          col.remove 1 ' Remove first item
        Next k
End Function


Function getShortPoint(x1 As Double, y1 As Double, x2 As Double, y2 As Double, length As Double) As Double()

    Dim dx As Double
    Dim dy As Double
    Dim rad As Double
    Dim ddd(1) As Double
    
    dx = x2 - x1
    dy = y2 - y1

    rad = Atn2(dy, dx)
    
    
    ddd(0) = x1 + length * Cos(rad)
    ddd(1) = y1 + length * Sin(rad)
    
    getShortPoint = ddd

End Function

Attribute VB_Name = "ClsFillet2"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private orgLayer As String
Private oldroad As AcadEntity
Private newroad As AcadEntity
Private fillet As AcadEntity



Private ptIntersection As Variant


Private np1 As New clsPoint
Private np2 As New clsPoint
Private np3 As New clsPoint


Private newroadsplit() As Double
Private oldroadsplit() As Double
Private filletsplit() As Double

Private isEdited As Boolean



Public Function load()

    Dim retArc As AcadEntity
    Dim tmp As Variant
    
    
    Dim pr As New clsPolygonReader

    
    Dim merge As New ClsMerger
    Dim resultd() As Double
    Dim test As Boolean
    
    Dim pt1 As New clsPoint
    Dim pt3 As New clsPoint
    
    
    Dim pr1 As New clsPolygonReader
    Dim pr2 As New clsPolygonReader
    
    Dim line1 As AcadLine
    Dim line2 As AcadLine
    Dim resultpl As AcadLine
    Dim ssetObj As AcadSelectionSet
    Dim result As AcadEntity

  
    Dim selec1 As New ClsSelEntity
    Dim selec2 As New ClsSelEntity
    Dim undoPoint As AcadEntity
    
    Dim seler As New ClsSelReal
    Dim frad As Double
    
    Dim selecs As New clsSelSets
    
    Dim eidx As Integer
    Dim freezelayer As AcadLayer
    Dim okcnt As Integer
    Dim ok As Boolean
    
    On Error GoTo EndOfFunction
    Debug.Print "==================START ================="
    
    isEdited = False
    okcnt = 0
    
    ok = selec1.selectPolyline("#Get Polyline 1: ")
    
    If ok = False Then
        ThisDrawing.Utility.prompt "선택에 오류가 발생했습니다."
        GoTo EndOfFunction
    
    End If
    
    Set newroad = selec1.getEntity
    Set pt1 = selec1.getPoint
    
    
    'deleteLayer TEMP_LAYER
    
    'newLayer TEMP_LAYER
    'newFreezeLayer "zzz_Freeze"
    Set undoPoint = ThisDrawing.ModelSpace.AddText("UU-U", selec1.getMovePoindD(5), 2)
    'undoPoint.layer = TEMP_LAYER
    
    
    ok = selec2.selectPolyline("#Get Polyline 2: ")
    
    If ok = False Then
        ThisDrawing.Utility.prompt "선택에 오류가 발생했습니다."
        GoTo EndOfFunction
    
    End If
    
    
    Set oldroad = selec2.getEntity
    Set pt3 = selec2.getPoint
    
    Debug.Print "!!! click " & pt3.x & ", " & pt3.y
    
    'pt3.x = 1145657.5787626
    'pt3.y = 1688571.88549874
    
    isEdited = hasProperties(newroad)
    
    
    ptIntersection = searchCrossVertext(newroad, oldroad)
    
    For i = 0 To UBound(ptIntersection) Step 3
        'addDonutA ptIntersection(i), ptIntersection(i + 1)          '!!!!!!!!!!!!!!!!!!!!!!
        
        ok = isContains(newroad, CDbl(ptIntersection(i)), CDbl(ptIntersection(i + 1)))
        If ok = True Then
            okcnt = okcnt + 1
        End If
    Next i
    
    
    If okcnt < 2 Then
        ThisDrawing.Utility.prompt "인접부분 확인바랍니다 - 접점: " & okcnt
        'oldroad.Delete
        'newroad.Delete
        GoTo EndOfFunction
    
    End If
    
    
    Set np3 = getNearPoint2(ptIntersection, pt3)
    
    'addDonut5 np3.x, np3.y
    
    
    pr1.init newroad
    Set line1 = pr1.getLine(pt1)
    'line1.layer = TEMP_LAYER
    
     
     
    pr2.init oldroad
    Set line2 = pr2.getLine(pt3)
    'line2.layer = TEMP_LAYER
     
    
     Set resultpl = getShortestLine(line2, pt3, np3)
    'resultpl.layer = TEMP_LAYER
    
    'addDonut5 pt3.x, pt3.y
 '    addDonut5 np3.x, np3.y
    
     frad = seler.selectFilletRadius
    
    
    Application.ActiveDocument.SendCommand "_fillet" & vbCr & "T" & vbCr & "N" & vbCr & "r" & vbCr & frad & vbCr & "(HandEnt """ & line1.Handle & """)" & vbCr & "(HandEnt """ & resultpl.Handle & """)" & vbCr
    
    
    Set retArc = selecs.selectArc
    'retArc.layer = TEMP_LAYER
    
    'Set retArc = selectArcObj
    
    'Set ssetObj = ThisDrawing.ActiveSelectionSet
    '
    'ssetObj.Select acSelectionSetLast
    '
    'For Each ent In ssetObj
    '   Set retArc = ent
    'Next
    
    If line2.Handle <> resultpl.Handle Then
        resultpl.Delete
    End If
    
    line1.Delete
    line2.Delete
    
    
    
    Set fillet = arc2line(retArc)  '아크를 라인으로 변경
    'fillet.layer = TEMP_LAYER
    
    ThisDrawing.SendCommand "sob" & vbCr
    
    filletsplit = fillet.Coordinates
    
    retArc.Delete
    
    
    Debug.Print "fillet created"
    
    newp1 = findVertex2(newroad, fillet, pt1)   '아크와 도로(새도로)의 접점 추가
    newp2 = findVertex2(oldroad, fillet, pt3)   '아크와 도로(구도로)의 접점 추가
   
   
    np1.initXy newp1(0), newp1(1)
    np2.initXy newp2(0), newp2(1)
    
    
    Debug.Print "np1: " & np1.x & ", " & np1.y
    Debug.Print "np2: " & np2.x & ", " & np2.y
    
    
    'If np1.x = 0 Or np1.y = 0 Or np2.x = 0 Or np2.y = 0 Then
    '    Debug.Print "!!!!!!!!!!!!!!!!!!!!!!!!!!!!!!!!!!!!!!!!!"
     
    'End If
    
    
    
    
    'addDonut5 np1.x, np1.y
    'addDonut5 np2.x, np2.y
   
    Set np3 = getFarPoint2Ex(newroad, ptIntersection, np1)     '기존도로 아크 접점에서 먼 지점을 찾는다
    
    ptIntersection = searchCrossVertext(newroad, fillet)
    
    
    'For i = 0 To UBound(ptIntersection) Step 3
    '    addDonutA ptIntersection(i), ptIntersection(i + 1)          '!!!!!!!!!!!!!!!!!!!!!!
    'Next i
    
    If UBound(ptIntersection) > 0 Then
        Set np1 = getNearPoint2(ptIntersection, np3)
        addVertex fillet, np1.x, np1.y
        'addDonutA np1.x, np1.y
    End If
    
    ptIntersection = searchCrossVertext(oldroad, fillet)
  
    If UBound(ptIntersection) > 0 Then
        Set np2 = getNearPoint2(ptIntersection, np3)
        addVertex fillet, np2.x, np2.y
        'addDonutA np1.x, np1.y
    End If
    
    filletsplit = fillet.Coordinates
    
    
    addVertex oldroad, np3.x, np3.y     '기존도로에 접점추가
    addVertex oldroad, np2.x, np2.y
    addVertex newroad, np1.x, np1.y
    
    
    'addDonutA np1.x, np1.y
    'addDonutA np2.x, np2.y
    'addDonutA np3.x, np3.y
   
    
    Debug.Print "cross point created"
    
    pr.init newroad
    pr.setIndexByPoint np1
    pr.checkDirection pt3
    
    Debug.Print "newroad direction processed"
    
    
    sidx = pr.setIndexByPoint(np1)
    eidx = pr.setEIndexByPoint(np3)
    
    newroadsplit = pr.getLongLine2()
  
 
    Debug.Print "newroad split created"
   
    pr.init oldroad
    pr.setIndexByPoint np2
    pr.checkDirection pt1
    
    Debug.Print "oldroad direction processed"
    
    
    sidx = pr.setIndexByPoint(np2)
    eidx = pr.setEIndexByPoint(np3)
    
    oldroadsplit = pr.getShortLine2()
    
    'oldroadsplit = pr.splitInnerLine(np2, np3)
    'addLine oldroadsplit

    
    Debug.Print "oldroad split created"
        
        
    checkTailPointEx np2
    checkLastPoint
    'oldroadsplit = checkCrossPoint3Ex(oldroad, oldroadsplit, np3)
    checkCrossPoint
    
    Debug.Print "oldroad split checked"
    
    checkTailPointEx np1
    checkLastPoint2
    'newroadsplit = checkCrossPoint4Ex(newroad, newroadsplit, np2)
    checkCrossPoint2
    
    Debug.Print "newroad split checked"
        
    size1 = UBound(newroadsplit)
    size2 = UBound(filletsplit)
    size3 = UBound(oldroadsplit)
    
    merge.setSize size1 + size2 + size3 + 2
    
    
    'ThisDrawing.ModelSpace.AddLightWeightPolyline oldroadsplit
    
    
    merge.add newroadsplit
    merge.add filletsplit
    merge.add oldroadsplit
    
    
    Set result = addLine(merge.getMerged)
    result.Closed = True
    'result.layer = TEMP_LAYER
    'newroad.Delete
    fillet.Delete
    
    
    'Set temp = ThisDrawing.ActiveLayer
    orgLayer = newroad.layer
    result.layer = getAddLayerName(orgLayer)
    newroad.layer = getDelLayerName(orgLayer)
    
    If (orgLayer Like LYR_ADD & "*") Or isEdited = False Then
        newroad.Delete
    End If
    
    
    
EndOfFunction:
    
    If undoPoint Is Nothing = False Then
        undoPoint.Delete
    End If
    'deleteLayer TEMP_LAYER
    

    Debug.Print "DONE"
    
    
    
End Function


Private Function getArcBy3P(p1() As Double, p2() As Double, p3() As Double) As AcadArc
    Dim centerPoint(0 To 2) As Double
    Dim retOjb As AcadArc
    
    x1 = p1(0)
    y1 = p1(1)
    
    x2 = p2(0)
    y2 = p2(1)
     
    x3 = p3(0)
    y3 = p3(1)
    
    d1 = (x2 - x1) / (y2 - y1)
    d2 = (x3 - x2) / (y3 - y2)
    
    cx = ((y3 - y1) + (x2 + x3) * d2 - (x1 + x2) * d1) / (2 * (d2 - d1))
    cy = -d1 * (cx - (x1 + x2) / 2) + (y1 + y2) / 2
     
    r = VBA.Sqr((x1 - cx) ^ 2 + (y1 - cy) ^ 2)
    
    centerPoint(0) = cx
    centerPoint(1) = cy
    
    StartAngle = ArcTan2((x1 - cx), (y1 - cy))
    EndAngle = ArcTan2((x3 - cx), (y3 - cy))
    
    If StartAngle >= 0 And EndAngle >= 0 Then
        If StartAngle > EndAngle Then
            tmp = StartAngle
            StartAngle = EndAngle
            EndAngle = tmp
        End If
    ElseIf StartAngle < 0 And EndAngle < 0 Then
        If StartAngle > EndAngle Then
            tmp = StartAngle
            StartAngle = EndAngle
            EndAngle = tmp
        End If
    ElseIf StartAngle > 0 And EndAngle < 0 Then
        If (PI - StartAngle) + (PI + EndAngle) > PI Then
            tmp = StartAngle
            StartAngle = EndAngle
            EndAngle = tmp
        End If
    ElseIf StartAngle < 0 And EndAngle > 0 Then
        If Abs(StartAngle) + EndAngle > PI Then
            tmp = StartAngle
            StartAngle = EndAngle
            EndAngle = tmp
        End If
            
    End If
    
    
    Set retOjb = ThisDrawing.ModelSpace.AddArc(centerPoint, r, StartAngle, EndAngle)
     
    
    Set getArcBy3P = retOjb

End Function

Function checkTailPointEx(pt As clsPoint)
    
    Dim idx As Integer
    Dim lastx As Double
    Dim lasty As Double
    Dim size As Integer
    Dim dist1 As Double
    Dim dist2 As Double
    Dim x As Double
    Dim y As Double
    Dim ret() As Double
    
    size = UBound(filletsplit)
    
    lastx = filletsplit(size - 1)
    lasty = filletsplit(size)

    dist1 = getDistance(pt.x, pt.y, lastx, lasty)
    
    lastx = filletsplit(0)
    lasty = filletsplit(1)
    
    dist2 = getDistance(pt.x, pt.y, lastx, lasty)
    
    
    'addDonutA np1.x, np1.y
    
    If dist1 < dist2 Then
        For i = size - 1 To 0 Step -2
            x = filletsplit(i)
            y = filletsplit(i + 1)
            
            If x = pt.x And y = pt.y Then
            
                Debug.Print ""
                Exit For
                
            End If
            idx = idx - 2
            
        Next i
    
    Else
        
        
        For i = 0 To size Step 2
            x = filletsplit(i)
            y = filletsplit(i + 1)
            
            'addDonut5 x, y
            
            'Debug.Print "*" & pt.x & ", " & pt.y
            'Debug.Print "+" & x & ", " & y
            
            b1 = (x = pt.x)
            b2 = (y = pt.y)
            
            If isEqualsDouble(x, y, pt.x, pt.y) Then
            
                Debug.Print ""
                Exit For
                
            End If
            idx = idx + 2
        
        Next i
        
        If idx < size Then
            ReDim ret(size - idx) As Double
            
            For i = idx To size Step 2
            
                ret(i - idx) = filletsplit(i)
                ret(i - idx + 1) = filletsplit(i + 1)
                Debug.Print ""
            Next i
            
            filletsplit = ret
        End If
    
    
    End If
  
    
End Function

Function checkTailPoint()
    
    Dim idx As Integer
    Dim lastx As Double
    Dim lasty As Double
    Dim size As Integer
    Dim dist1 As Double
    Dim dist2 As Double
    Dim x As Double
    Dim y As Double
    Dim ret() As Double
    
    size = UBound(filletsplit)
    
    lastx = filletsplit(size - 1)
    lasty = filletsplit(size)

    dist1 = getDistance(np1.x, np1.y, lastx, lasty)
    
    lastx = filletsplit(0)
    lasty = filletsplit(1)
    
    dist2 = getDistance(np1.x, np1.y, lastx, lasty)
    
    
    'addDonutA np1.x, np1.y
    
    If dist1 < dist2 Then
        For i = size - 1 To 0 Step -2
            x = filletsplit(i)
            y = filletsplit(i + 1)
            
            If x = np1.x And y = np1.y Then
            
                Debug.Print ""
                Exit For
                
            End If
            idx = idx - 2
            
        Next i
    
    Else
        
        
        For i = 0 To size Step 2
            x = filletsplit(i)
            y = filletsplit(i + 1)
            
            'addDonut5 x, y
            
            Debug.Print "*" & np1.x & ", " & np1.y
            Debug.Print "+" & x & ", " & y
            
            b1 = (x = np1.x)
            b2 = (y = np1.y)
            
            If isEqualsDouble(x, y, np1.x, np1.y) Then
            
                Debug.Print ""
                Exit For
                
            End If
            idx = idx + 2
        
        Next i
        
        If idx < size Then
            ReDim ret(size - idx) As Double
            
            For i = idx To size Step 2
            
                ret(i - idx) = filletsplit(i)
                ret(i - idx + 1) = filletsplit(i + 1)
                Debug.Print ""
            Next i
            
            filletsplit = ret
        End If
    
    
    End If
  
    
End Function

Function checkLastPoint()

    Dim retvalue() As Double
    Dim lastx As Double
    Dim lasty As Double
    Dim size As Integer
    Dim dist1 As Double
    Dim dist2 As Double
    
    size = UBound(filletsplit)
    
    lastx = filletsplit(size - 1)
    lasty = filletsplit(size)
    
    'addDonutA lastx, lasty
    'addDonutA np2.x, np2.y

    dist1 = getDistance(np2.x, np2.y, lastx, lasty)
    
    lastx = filletsplit(0)
    lasty = filletsplit(1)
    
    dist2 = getDistance(np2.x, np2.y, lastx, lasty)
    
    
    If dist1 <> 0 And dist2 <> 0 Then   '겹치지 않을때
    
        If dist1 < dist2 Then
            filletsplit(size - 1) = np2.x
            filletsplit(size) = np2.y
        
        Else
            filletsplit(0) = np2.x
            filletsplit(1) = np2.y
        
        End If
  
    End If
  
End Function



Function checkLastPoint2()  '

    Dim retvalue() As Double
    Dim firstx As Double
    Dim firsty As Double
    Dim size As Integer
    Dim dist1 As Double
    Dim dist2 As Double
    
    size = UBound(filletsplit)
    
    firstx = filletsplit(size - 1)
    firsty = filletsplit(size)
    
    'addDonutA firstx, firsty
    'addDonutA np1.x, np1.y

    dist1 = getDistance(np1.x, np1.y, firstx, firsty)
    
    firstx = filletsplit(0)
    firsty = filletsplit(1)
    
    dist2 = getDistance(np1.x, np1.y, firstx, firsty)
    
    
    If dist1 <> 0 And dist2 <> 0 Then   '겹치지 않을때
    
        If dist1 < dist2 Then
            filletsplit(size - 1) = np1.x
            filletsplit(size) = np1.y
        
        Else
            filletsplit(0) = np1.x
            filletsplit(1) = np1.y
        
        End If
  
    End If
  
End Function
 
 
Function checkCrossPoint()


    Dim tmpfillet As AcadLWPolyline
    Dim tmpoldroad As AcadLWPolyline
    Dim intersec As Variant
    
    Dim selidx As Integer
    Dim mindist As Double
    
    Dim plreader As New ClsPolylineReader
    
    Dim x, y As Double
    Dim nx As Double
    Dim ny As Double
    
    Dim b1, b2 As Boolean
    
    selidx = -1
    mindist = 99999
    
    Set tmpfillet = ThisDrawing.ModelSpace.AddLightWeightPolyline(filletsplit)
    Set tmpoldroad = ThisDrawing.ModelSpace.AddLightWeightPolyline(oldroadsplit)
    
    intersec = searchCrossVertext(tmpfillet, oldroad)
    
    'addDonut5 np3.x, np3.y
    
    For i = 0 To UBound(intersec) Step 3
    
        x = intersec(i)
        y = intersec(i + 1)
    
        b1 = isContains(tmpfillet, CDbl(x), CDbl(y))
        b2 = isContains(tmpoldroad, CDbl(x), CDbl(y))
        
        If b1 = False Or b2 = False Then
            
        Else
        
            dist = getDistance(np3.x, np3.y, intersec(i), intersec(i + 1))
            
            'addDonutA intersec(i), intersec(i + 1)
            
            If dist < mindist Then
            
                mindist = dist
                selidx = i
            End If
        
        End If
    Next i
    
    
    If selidx = -1 Then
        Return
    End If
    
    
    nx = intersec(selidx)
    ny = intersec(selidx + 1)
    
    'addDonutA nx, ny
    
    
    
    
    addVertex tmpfillet, nx, ny
    addVertex tmpoldroad, nx, ny
    
    plreader.init tmpfillet
    filletsplit = plreader.getLongDDLine(nx, ny)
    'ThisDrawing.ModelSpace.AddLightWeightPolyline filletsplit
    
    plreader.init tmpoldroad
    oldroadsplit = plreader.getLongDDLine(nx, ny)
    'ThisDrawing.ModelSpace.AddLightWeightPolyline oldroadsplit
    
    addVertex oldroad, nx, ny
    
    
    tmpfillet.Delete
    tmpoldroad.Delete
    
    
    Debug.Print ""
    
    
    
End Function


Function checkCrossPoint2()


    Dim tmpfillet As AcadLWPolyline
    Dim tmpnewroad As AcadLWPolyline
    Dim intersec As Variant
    
    Dim selidx As Integer
    Dim mindist As Double
    
    Dim plreader As New ClsPolylineReader
    
    Dim x, y As Double
    Dim nx As Double
    Dim ny As Double
    
    Dim b1, b2 As Boolean
    
    selidx = -1
    mindist = 99999
    
    Set tmpfillet = ThisDrawing.ModelSpace.AddLightWeightPolyline(filletsplit)
    Set tmpnewroad = ThisDrawing.ModelSpace.AddLightWeightPolyline(newroadsplit)
    
    intersec = searchCrossVertext(tmpfillet, newroad)
    
    'addDonut5 np2.x, np2.y
    
    For i = 0 To UBound(intersec) Step 3
    
        x = intersec(i)
        y = intersec(i + 1)
    
        b1 = isContains(tmpfillet, CDbl(x), CDbl(y))
        b2 = isContains(tmpnewroad, CDbl(x), CDbl(y))
        
        If b1 = False Or b2 = False Then
            
        Else
        
            dist = getDistance(np2.x, np2.y, intersec(i), intersec(i + 1))
            
            'addDonutA intersec(i), intersec(i + 1)
            
            If dist < mindist Then
            
                mindist = dist
                selidx = i
            End If
        
        End If
    Next i
    
    
    If selidx = -1 Then
        Return
    End If
    
    
    nx = intersec(selidx)
    ny = intersec(selidx + 1)
    
    'addDonutA nx, ny
    
    
    
    
    addVertex tmpfillet, nx, ny
    addVertex tmpnewroad, nx, ny
    
    plreader.init tmpfillet
    filletsplit = plreader.getLongDDLine(nx, ny)
    'ThisDrawing.ModelSpace.AddLightWeightPolyline filletsplit
    
    plreader.init tmpnewroad
    newroadsplit = plreader.getLongDDLine(nx, ny)
    'ThisDrawing.ModelSpace.AddLightWeightPolyline oldroadsplit
    
    addVertex newroad, nx, ny
    
    
    tmpfillet.Delete
    tmpnewroad.Delete
    
    
    Debug.Print ""
    
    
    
End Function



Function checkCrossPoint3Ex(road As AcadEntity, roadsplit() As Double, np As clsPoint) As Double()


    Dim tmpfillet As AcadLWPolyline
    Dim tmproad As AcadLWPolyline
    Dim intersec As Variant
    
    Dim selidx As Integer
    Dim mindist As Double
    
    Dim plreader As New ClsPolylineReader
    
    Dim x, y As Double
    Dim nx As Double
    Dim ny As Double
    
    Dim b1, b2 As Boolean
    
    selidx = -1
    mindist = 99999
    
    Set tmpfillet = ThisDrawing.ModelSpace.AddLightWeightPolyline(filletsplit)
    Set tmproad = ThisDrawing.ModelSpace.AddLightWeightPolyline(roadsplit)
    
    intersec = searchCrossVertext(tmpfillet, road)
    
    'addDonut5 np.x, np.y
    
    For i = 0 To UBound(intersec) Step 3
    
        x = intersec(i)
        y = intersec(i + 1)
    
        'b1 = isContains(tmpfillet, CDbl(x), CDbl(y))
        'b2 = isContains(tmproad, CDbl(x), CDbl(y))
        
        
        dist = getDistance(np.x, np.y, intersec(i), intersec(i + 1))
            
        'addDonutA intersec(i), intersec(i + 1)
            
        If dist < mindist Then
            
            mindist = dist
            selidx = i
        End If
        
        
    Next i
    
    
    If selidx = -1 Then
        Return
    End If
    
    
    nx = intersec(selidx)
    ny = intersec(selidx + 1)
    
    'addDonutA nx, ny
    
    np2.x = nx
    np2.y = ny
    
    
    
    addVertex tmpfillet, nx, ny
    addVertexT2 tmproad, nx, ny
    
    plreader.init tmpfillet
    filletsplit = plreader.getLongDDLine(nx, ny)
    'ThisDrawing.ModelSpace.AddLightWeightPolyline filletsplit
    
    plreader.init tmproad
    roadsplit = plreader.getLongDDLine(nx, ny)
    'ThisDrawing.ModelSpace.AddLightWeightPolyline oldroadsplit
    
    'addVertex newroad, nx, ny
    
    
    tmpfillet.Delete
    tmproad.Delete
    
    
    Debug.Print ""
    
    checkCrossPoint3Ex = roadsplit
    
End Function


Function checkCrossPoint4Ex(road As AcadEntity, roadsplit() As Double, np As clsPoint) As Double()


    Dim tmpfillet As AcadLWPolyline
    Dim tmproad As AcadLWPolyline
    Dim intersec As Variant
    
    Dim selidx As Integer
    Dim mindist As Double
    
    Dim plreader As New ClsPolylineReader
    
    Dim x, y As Double
    Dim nx As Double
    Dim ny As Double
    
    Dim b1, b2 As Boolean
    
    selidx = -1
    mindist = 99999
    
    Set tmpfillet = ThisDrawing.ModelSpace.AddLightWeightPolyline(filletsplit)
    Set tmproad = ThisDrawing.ModelSpace.AddLightWeightPolyline(roadsplit)
    
    intersec = searchCrossVertext(tmpfillet, road)
    
    'addDonut5 np.x, np.y
    
    For i = 0 To UBound(intersec) Step 3
    
        x = intersec(i)
        y = intersec(i + 1)
    
        'b1 = isContains(tmpfillet, CDbl(x), CDbl(y))
        'b2 = isContains(tmproad, CDbl(x), CDbl(y))
        
        
        dist = getDistance(np.x, np.y, intersec(i), intersec(i + 1))
            
        'addDonutA intersec(i), intersec(i + 1)
            
        If dist < mindist Then
            
            mindist = dist
            selidx = i
        End If
        
        
    Next i
    
    
    If selidx = -1 Then
        Return
    End If
    
    
    nx = intersec(selidx)
    ny = intersec(selidx + 1)
    
    'addDonutA nx, ny
    
    np2.x = nx
    np2.y = ny
    
    
    
    addVertex tmpfillet, nx, ny
    addVertexT2 tmproad, nx, ny
    
    plreader.init tmpfillet
    filletsplit = plreader.getLongDDLine(nx, ny)
    'Set tmpf = ThisDrawing.ModelSpace.AddLightWeightPolyline(filletsplit)
    'tmpf.color = acBlue
    
    plreader.init tmproad
    roadsplit = plreader.getLongDDLine(nx, ny)
    'Set tmpf = ThisDrawing.ModelSpace.AddLightWeightPolyline(oldroadsplit)
    'tmpf.color = acRed
    
    'addVertex newroad, nx, ny
    
    
    tmpfillet.Delete
    tmproad.Delete
    
    
    Debug.Print ""
    
    checkCrossPoint4Ex = roadsplit
    
End Function

Attribute VB_Name = "ClsMerger"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private ret() As Double
Private index As Integer



Public Function setSize(size As Integer)

    ReDim ret(0 To size) As Double
    index = 0

End Function


Public Function add(d() As Double)

    Dim reverse As Boolean
    Dim size As Integer
    
    reverse = False
    size = UBound(d)
    
    If index > 1 Then
    
        x = ret(index - 2)
        y = ret(index - 1)
        
        d1 = getDistance(x, y, d(0), d(1))
        d2 = getDistance(x, y, d(size - 1), d(size))
        
        If d2 < d1 Then
            reverse = True
        End If
    
    End If
    
    
    If reverse = False Then
        For i = 0 To size Step 2
            ret(index) = d(i)
            index = index + 1
            ret(index) = d(i + 1)
            index = index + 1
            
            'addDonutA d(i), d(i + 1)
        Next
    
    Else
        For i = size - 1 To 0 Step -2
            ret(index) = d(i)
            index = index + 1
            ret(index) = d(i + 1)
            index = index + 1
            'addDonutA d(i), d(i + 1)
        Next
    
    End If
    

End Function


Public Function getMerged() As Double()


    getMerged = ret

End Function


Public Function merge(d1() As Double, d2() As Double, d3() As Double) As Double()

    Dim size1 As Integer
    Dim size2 As Integer
    Dim size3 As Integer
    
    
    size1 = UBound(d1)
    size2 = UBound(d2)
    size3 = UBound(d3)
    
    
    ReDim ret(0 To size1 + size2 + size3 + 2) As Double
    
    
    idx = 0
    For i = 0 To size1 Step 2
        ret(idx) = d1(i)
        idx = idx + 1
        ret(idx) = d1(i + 1)
        idx = idx + 1
        
        addDonut5 d1(i), d1(i + 1)
    Next
    
    
    
    
    For i = 0 To size2 Step 2
        ret(idx) = d2(i)
        idx = idx + 1
        ret(idx) = d2(i + 1)
        idx = idx + 1
        
        addDonut5 d2(i), d2(i + 1)
        
        
    Next
    
    For i = 0 To size3 Step 2
        ret(idx) = d3(i)
        idx = idx + 1
        ret(idx) = d3(i + 1)
        idx = idx + 1
        
        addDonut5 d3(i), d3(i + 1)
    Next
    
    
    merge = ret
    


End Function

Attribute VB_Name = "ClsMultiBreaker"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private plroad() As AcadEntity

Private ptd1() As Double
Private ptd2() As Double
Private ptdn1() As Double
Private ptdn2() As Double


Private pt1 As New clsPoint
Private pt2 As New clsPoint



Function load()
    
    Dim ttt As Variant
    Dim reg As AcadRegion
    Dim ment As AcadLWPolyline
    
    Dim conv As New ClsConverter
    
    Dim ce As New ClsBreaker
    
    
    'On Error GoTo EndOfFunction
    Debug.Print "==================START ================="
    
    
    plroad = selectPolylineObs
    
    ttt = ThisDrawing.ModelSpace.AddRegion(plroad)
    
    Set reg = ttt(0)
    
    For i = 1 To UBound(ttt)
        reg.Boolean acUnion, ttt(i)
    Next i
    
    
    Set ment = conv.reg2polyline(reg)
    reg.Delete
     
    
    
    ce.setBaseEntity ment
    ce.load
    
    ment.Delete
    
EndOfFunction:
    
    Debug.Print "DONE"
    
End Function

Attribute VB_Name = "ClsODInfo"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private acadObj As Object
Private tblname As String

Private amap As AutocadMAP.AcadMap
Private proj As AutocadMAP.Project
Private ODtb As AutocadMAP.ODTable

Private ODfdfs As ODFieldDefs
Private odrecrds As ODRecords




Function init(obj As Object, str As String)
    Set acadObj = obj
    tblname = str
    
    
    Set amap = ThisDrawing.Application.GetInterfaceObject("AutoCADMap.Application")
    
    Set proj = amap.Projects(ThisDrawing)
    
End Function



Function setTableInstance() As Boolean
    Dim tbl As AutocadMAP.ODTable
    For Each tbl In proj.ODTables
        If UCase(tbl.name) = UCase(tblname) Then
            Set ODtb = tbl
            setTableInstance = True
            Exit Function
        End If
    Next
    
    'MsgBox "예기치않은 오류가 발생했습니다. 개발자에게 문의하세요."
    Debug.Print tbl.name & " IS NOT FOUND"
    'Set tbl = proj.ODTables.add(tblname, "External Xdata", ODfdfs, True)
    
    Set ODtb = tbl
    setTableInstance = False
     
End Function
 
 
Function setFieldDefs(fdfs As ODFieldDefs)
    Set ODfdfs = fdfs

End Function


Function setODFieldDefs()

    Set ODfdfs = amap.Projects(ThisDrawing).MapUtil.NewODFieldDefs
    
    Set ODfdf = ODfdfs.add("Entity", "Entity name", "", 0)
    Set ODfdf = ODfdfs.add("Color", "Object color", acRed, 1)
    Set ODfdf = ODfdfs.add("Layer", "Object layer", "0", 2)
    
End Function


Public Function remove()

    Set odrecrds = ODtb.GetODRecords
    odrecrds.init acadObj, True, False
    
    odrecrds.remove
    odrecrds = Nothing
End Function


Public Function getInfo() As Collection

    Dim col As New Collection
    Set odrecrds = ODtb.GetODRecords
    odrecrds.init acadObj, True, False
    
    If odrecrds.IsDone = False Then
        Set ODrc = odrecrds.record
        Set ODfdfs = ODtb.ODFieldDefs
        
        count = ODfdfs.count
        
        For i = 0 To count - 1
            Set fieldd = ODfdfs.Item(i)
            Set fieldv = ODrc.Item(i)
        
            Debug.Print i & ")" & fieldd.name & ": " & fieldv.value
            
            col.add fieldv.value
            
        Next
    End If
    
    Set odrecrds = Nothing
    
    Set getInfo = col
    
End Function


Public Function getInfoByName(fname As String) As Variant

    Dim ret As Variant
    
    If ODtb Is Nothing Then
    
        getInfoByName = -1
        Exit Function
    End If
    
    
    Set odrecrds = ODtb.GetODRecords
    odrecrds.init acadObj, True, False
    
    If odrecrds.IsDone = False Then
        Set ODrc = odrecrds.record
        Set ODfdfs = ODtb.ODFieldDefs
        
        count = ODfdfs.count
        
        For i = 0 To count - 1
            Set fieldd = ODfdfs.Item(i)
            Set fieldv = ODrc.Item(i)
        
            If fieldd.name = fname Then
                ret = fieldv.value
                'Debug.Print i & ")" & fieldd.name & ": " & fieldv.value
                
                Exit For
                
            End If
            
            
        Next
    End If
    
    Set odrecrds = Nothing
    
    getInfoByName = ret
    
End Function


Public Function setInfo(col As Collection) As Boolean

    Dim obj As Object
    Dim bret As Boolean
    Set odrecrds = ODtb.GetODRecords
    
    Debug.Print "id: " & acadObj.ObjectID
    
    bret = False
    odrecrds.init acadObj, True, False
    
    If odrecrds.IsDone = False Then
        Set ODrc = odrecrds.record
        Set ODfdfs = ODtb.ODFieldDefs
        
        
        count = ODfdfs.count
        
        For i = 0 To count - 1
            Set fieldd = ODfdfs.Item(i)
            Set fieldv = ODrc.Item(i)
        
            'obj = "TEST" 'col.Item(i + 1)
            'Debug.Print i & ")" & fieldd.name & ": " & fieldv.value
            ODrc.Item(i).value = col.Item(i + 1)
        Next
        
        odrecrds.Update ODrc
        bret = True
   
    End If
    
    Set odrecrds = Nothing
    
    Debug.Print "type: " & TypeName(acadObj.ObjectID)
    
    setInfo = bret
    
End Function

Attribute VB_Name = "ClsObjectCombiner"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private plroad() As AcadEntity
Private ddd1() As Double
Private ddd2() As Double


Private d1size As Integer
Private d2size As Integer

Function load()

    Dim size As Integer
    Dim ent1 As AcadLWPolyline
    Dim ent2 As AcadLWPolyline
    


    Dim x1 As Double
    Dim y1 As Double
    Dim x2 As Double
    Dim y2 As Double

    Dim dist As Double


    On Error GoTo errControl

    plroad = selectPolylineObs
    
    size = UBound(plroad)
    
    
    For i = 0 To size
    
        Set ent1 = plroad(i)
        'ddd1 = ent1.Coordinates
        'd1size = UBound(ddd1)
        
        
        For j = i + 1 To size
           'Debug.Print "d1size: " & d1size; ", d2size: " & d2size
        
           Set ent2 = plroad(j)
           'ddd2 = ent2.Coordinates
           'd2size = UBound(ddd2)
        
           processEx ent1, ent2
        
        Next j
    
    Next i
    
errControl:
    Debug.Print "DONE"

End Function


Function processEx(ent1 As AcadLWPolyline, ent2 As AcadLWPolyline) As Boolean


    Dim cir1 As AcadCircle
    Dim cir2 As AcadCircle

    Dim col1 As New Collection
    Dim col2 As New Collection
    
    Dim group As New Collection
    Dim gcnt As Integer
    Dim dist As Double
    
    Dim pr As New clsPolygonReader
    
    Dim x1 As Double
    Dim y1 As Double
    Dim x2 As Double
    Dim y2 As Double
    
    
    Dim g1p1 As New clsPoint
    Dim g1p2 As New clsPoint
    
    Dim g2p1 As New clsPoint
    Dim g2p2 As New clsPoint
    
    Dim np As New clsPoint
    Dim idx As Integer
    
    pr.init ent1
    pr.setIndex 0
    
    Set col1 = pr.getEdgeCollection
    
    pr.init ent2
    pr.setIndex 0
    
    Set col2 = pr.getEdgeCollection
    

    For i = 1 To col1.count Step 2
        x1 = col1(i)
        y1 = col1(i + 1)
        
        For j = 1 To col2.count Step 2
            x2 = col2(j)
            y2 = col2(j + 1)

            'Set cir1 = addDonut5(x1, y1)
            'Set cir2 = addDonut5(x2, y2)
            
            dist = getDistance(x1, y1, x2, y2)
            
            If dist < 1 Then
                group.add x1
                group.add y1
                group.add x2
                group.add y2
            End If

        Next j
    Next i
    
    
    gcnt = group.count
    Debug.Print "group cnt: " & gcnt
    i = 0
    If group.count = 8 Then
    
        
        g1p1.x = group(i + 1)
        g1p1.y = group(i + 2)
        g1p2.x = group(i + 3)
        g1p2.y = group(i + 4)
        
        g2p1.x = group(i + 5)
        g2p1.y = group(i + 6)
        g2p2.x = group(i + 7)
        g2p2.y = group(i + 8)
        
         
        If nearArc(ent1, g1p1, g2p1) = True Then
            'If nearArc(ent2, g1p2, g2p2) = False Then
                movePoint ent2, g1p2, g1p1
            'End If
        Else
            movePoint ent1, g1p1, g1p2
        
        End If
        
        If nearArc(ent1, g2p1, g1p1) = True Then
            'If nearArc(ent2, g2p2, g1p2) = False Then
                movePoint ent2, g2p2, g2p1
            'End If
        Else
            movePoint ent1, g2p1, g2p2
        
        End If
        

        Debug.Print ""
        
        'idx = pr.getSIndex
        'ddd1(idx) = g2p1.x
        'ddd1(idx + 1) = g2p1.y
            
        'ent1.Coordinates = ddd1
        'ent1.Update
        
        
            
        
        
        'addDonut5 p1.x, p1.y
        'addDonut5 x2, y2
         
    End If


End Function


Function movePoint(ent As AcadLWPolyline, pt1 As clsPoint, pt2 As clsPoint)

    Dim pr As New clsPolygonReader
    Dim idx As Integer
    Dim ddd() As Double
    
    pr.init ent
    pr.setIndexByPoint pt1
    idx = pr.getSIndex
    
    ddd = ent.Coordinates
        
        
    'addDonut5 ddd(idx), ddd(idx + 1)
        
    ddd(idx) = pt2.x
    ddd(idx + 1) = pt2.y
    
    ent.Coordinates = ddd
    ent.Update
     

End Function


Function nearArc(ent As AcadLWPolyline, pt1 As clsPoint, pt2 As clsPoint) As Boolean

    Dim pr As New clsPolygonReader
    Dim np As New clsPoint

    Dim ret As Boolean
    
    ret = False

    pr.init ent
    pr.setIndexByPoint pt1
    pr.setIndex pr.getSIndex
    
    Set np = pr.nextPoint
    If np.x = pt2.x And np.y = pt2.y Then
        pr.setIndexByPoint pt1
        pr.setIndex pr.getSIndex
        pr.setReverse
        
        Set np = pr.nextPoint
    End If
    
    
    'addDonutA pt1.x, pt1.y
    'addDonutA pt2.x, pt2.y
    
    'addDonut5 np.x, np.y
    
    
    dist = getDistance(pt1.x, pt1.y, np.x, np.y)
    
    If dist < 1 Then
        ret = True
        
    End If
    
    nearArc = ret
    
    

End Function


Function process() As Boolean

    Dim ret As Boolean
    
    ret = False

    For k = 0 To d1size Step 2
        
        x1 = ddd1(k)
        y1 = ddd1(k + 1)
        
        For l = 0 To d2size Step 2
        
            x2 = ddd2(l)
            y2 = ddd2(l + 1)
        
        
            If x1 = x2 And y1 = y2 Then
                Exit For
            End If
            
            dist = getDistance(x1, y1, x2, y2)
        
            'Debug.Print "dist: " & dist
            If dist < 0.8 Then
                ddd2(l) = x1
                ddd2(l + 1) = y1
                ret = True
                
                'addDonutA x1, y1
                'addDonutA x2, y2
                
            End If
    
    
        Next l
  
    
    Next k
            
    process = ret

End Function

Attribute VB_Name = "ClsObjectData"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private oid As Variant
Private mid As Variant

Public Function setData(o As Variant, m As Variant)

    oid = o
    mid = m

End Function

Attribute VB_Name = "ClsOverpassStep"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private entpo As AcadEntity '선택한 폴리곤

Private ptd1() As Double
Private ptd2() As Double
Private ptdn1() As Double
Private ptdn2() As Double


Private pt1 As New clsPoint
Private pt2 As New clsPoint


Private ent As AcadEntity
Private ddd() As Double
Private cidx As Integer
Private sidx As Integer
Private eidx As Integer
Private lidx As Integer

Private curpos As New clsPoint
Private nextpt As New clsPoint
Private curpt As New clsPoint


Private lastpt As New clsPoint

Private interval As Double
Private length As Double
Private rotaterad As Double

Private remaindist As Double

Private isLeft As Boolean





Function load()
    Dim ss As New clsSelSets
    Dim pr As New clsPolygonReader
    Dim ent As AcadEntity
    Dim ddd() As Double
    Dim ret As AcadEntity
    Dim ptt1(1) As Double
    Dim ptt2() As Double
    
    
    'On Error GoTo EndOfFunction
    Debug.Print "==================START ================="
    
    
    Set entpo = ss.selectOnePolyline
    
    If entpo Is Nothing Then
        ThisDrawing.Utility.prompt "선택 오류가 발생했습니다. 하나만 선택해주세요"
        GoTo EndOfFunction
    End If
    
    ThisDrawing.SetVariable "osmode", 543
    ptd1 = ThisDrawing.Utility.getPoint(, "Enter a point1: ")
    ptd2 = ThisDrawing.Utility.getPoint(, "Enter a point2: ")
    
    Set ent = entpo.Copy
    
    
 
    
    Debug.Print "ptd1(0) = " & ptd1(0)
    Debug.Print "ptd1(1) = " & ptd1(1)
    Debug.Print "ptd2(0) = " & ptd2(0)
    Debug.Print "ptd2(1) = " & ptd2(1)
    
    
    'addDonutA ptd1(0), ptd1(1)
    'addDonutA ptd2(0), ptd2(1)
    
    ptdn1 = addVertex(ent, ptd1(0), ptd1(1))
    ptdn2 = addVertex(ent, ptd2(0), ptd2(1))
    
    If ptdn1(0) = 0 Or ptdn1(1) = 0 Or ptdn2(0) = 0 Or ptdn2(1) = 0 Then
        ent.Delete
        ThisDrawing.Utility.prompt "포인트 선택 오류가 발생했습니다."
        GoTo EndOfFunction
    End If
    
    pt1.initPt ptdn1
    pt2.initPt ptdn2
    
  
    
    addDonut pt1.x, pt1.y
    addDonut pt2.x, pt2.y
    
    pr.init ent
    pr.setIndexByPoint pt1
    pr.setEIndexByPoint pt2
    
    ddd = pr.getShortLine2()
    
    Set ret = ThisDrawing.ModelSpace.AddLightWeightPolyline(ddd)
    ret.color = acRed
    ptt1(0) = ddd(0)
    ptt1(1) = ddd(1)
    
    init ret
    
    repeat = True
        
    
    Do While (repeat)
    
        repeat = addcrossline
    
    Loop
     
    ent.Delete
    ret.Delete
    
    
EndOfFunction:
    
    Debug.Print "DONE"
    
End Function


Function init(e As AcadEntity)

    Dim str() As String
    
    Set ent = e
    ddd = ent.Coordinates
    
    sidx = 0
    eidx = UBound(ddd)
    
    curpt.x = ddd(0)
    curpt.y = ddd(1)
    
    curpos.x = ddd(0)
    curpos.y = ddd(1)
    
    nextpt.x = ddd(2)
    nextpt.y = ddd(3)
    
    cidx = 4
    
    str = getTempSplit
    
    
    interval = CDbl(str(0))
    length = CDbl(str(1))
    
    rotaterad = PI / 2
    
    isLeft = True
    remaindist = 0
    
    'Print ("has arc: " & hasArc(ent))
    
End Function
 

Function addcrossline() As Boolean

    Dim dx As Double
    Dim dy As Double
    Dim nx As Double
    Dim ny As Double
    Dim distsub As Double
    Dim rad As Double
    Dim ret As Boolean
    Dim entsub As AcadEntity
    Dim retv As Variant
    
    
    ret = False
        
    If nextpt.x = 0 Or nextpt.y = 0 Then
        addcrossline = ret
        Exit Function
    End If
    
    distsub = getDistance(curpos.x, curpos.y, nextpt.x, nextpt.y)
    
    If distsub > 0 Then
    
    
        dx = nextpt.x - curpos.x
        dy = nextpt.y - curpos.y
        
        rad = getParkingLineRadian(dx, dy)
        
        If dy = 0 Then
            If dx > 0 Then
                nx = curpos.x + length
            Else
                nx = curpos.x - length
            End If
        Else
            nx = curpos.x + length * Cos(rad)
        End If
        
        ny = curpos.y + length * Sin(rad)
        
        'addDonutA nx, ny
        
        
        getRotatedLine curpos.x, curpos.y, nx, ny
         
        
            lastpt.x = curpos.x
            lastpt.y = curpos.y
            lidx = cidx - 2
            
            
            ret = True
            
            
            If distsub >= interval Then
                If dy = 0 Then
                    If dx > 0 Then
                        curpos.x = curpos.x + interval
                    Else
                        curpos.x = curpos.x - interval
                    End If
                Else
                    curpos.x = curpos.x + interval * Cos(rad)
                End If
                
                curpos.y = curpos.y + interval * Sin(rad)
            
            Else
            
                remaindist = 0
            
                Do While (distsub < interval)
                
                    If cidx < eidx Then
                
                        curpt.x = nextpt.x
                        curpt.y = nextpt.y
                        
                        nextpt.x = ddd(cidx)
                        nextpt.y = ddd(cidx + 1)
                        
                        cidx = cidx + 2
                 
                        remaindist = getDistance(curpt.x, curpt.y, nextpt.x, nextpt.y)
                        If distsub + remaindist >= interval Then
                            
                            dx = nextpt.x - curpt.x
                            dy = nextpt.y - curpt.y
                            
                            rad = getParkingLineRadian(dx, dy)
                            
                            If dy = 0 Then
                                If dx > 0 Then
                                    curpos.x = curpt.x + (interval - distsub)
                                Else
                                    curpos.x = curpt.x - (interval - distsub)
                                End If
                            Else
                                curpos.x = curpt.x + (interval - distsub) * Cos(rad)
                            End If
                            
                            curpos.y = curpt.y + (interval - distsub) * Sin(rad)
                        End If
                        
                        'addDonut5 curpos.x, curpos.y
                         
                        
                        distsub = distsub + remaindist
                 
                        Debug.Print "sub: " & distsub
                 
                    Else
                        nextpt.x = 0
                        nextpt.y = 0
                        Exit Do
                    End If
                
                Loop
                
                'If nextpt.x > 0 And nextpy.y > 0 Then
                
                    
                
                'End If
                
            'End If
        End If      ' valid
        
    Else
    
    End If
    
    
    addcrossline = ret
    

End Function

Function getParkingLineRadian(dx As Double, dy As Double) As Double


    Dim rad As Double
    
        
    If dx = 0 Then
        rad = PI / 2
       
        If dy < 0 Then
            rad = -rad
        End If
        
    Else
        rad = Atn(dy / dx)
        If dx < 0 Then
            rad = PI + rad
        End If
    End If
    
    getParkingLineRadian = rad


End Function

Function getRotatedLine(x1 As Double, y1 As Double, x2 As Double, y2 As Double) As Boolean


    Dim ddd(3) As Double
    Dim ddd2() As Double
    Dim ddd3() As Double
    Dim basept(2) As Double
    Dim ent As AcadLWPolyline
    Dim retb As Boolean
    Dim cnt As Integer
    Dim offset As Integer
    Dim dist As Double
    Dim mindist As Double
    
    ddd(0) = x1
    ddd(1) = y1
    ddd(2) = x2
    ddd(3) = y2
    
    
    'addDonut5 x1, y1
    'addDonut5 x2, y2
    
    basept(0) = x1
    basept(1) = y1
    
    Set ent = ThisDrawing.ModelSpace.AddLightWeightPolyline(ddd)
    
    If isLeft = True Then
        ent.Rotate basept, rotaterad
    Else
        ent.Rotate basept, -rotaterad
    End If
    
    'ent.color = acRed
    
    ent.layer = getAddLayerName("RD_SISUL_L_계단_171105")
    
    
    ddd2 = getExtendLineOverpass(entpo, ent) '연장선
    
    'If ddd(0) = ddd2(0) And ddd(1) = ddd2(1) Then
    '    ddd(2) = ddd2(3)
    '    ddd(3) = ddd2(4)
    'Else
    '    ddd(0) = ddd2(0)
    '    ddd(1) = ddd2(1)
    'End If
    
    
    cnt = UBound(ddd2)
    Debug.Print "" & cnt
    offset = 0
    If UBound(ddd2) >= 5 Then
    
        'ddd(0) = ddd2(0)
        'ddd(1) = ddd2(1)
        'ddd(2) = ddd2(cnt - 2)
        'ddd(3) = ddd2(cnt - 1)
        'ent.Coordinates = ddd
        
    
        'ReDim ddd3((cnt + 1) * 2 / 3 - 1) As Double
    
        'For i = 0 To UBound(ddd2) Step 3
        '    ddd3(offset) = ddd2(i)
        '    ddd3(offset + 1) = ddd2(i + 1)
        
        '    offset = offset + 2
        
        'Next i
    
        'ddd(0) = ddd2(0)
        'ddd(1) = ddd2(1)
        'ddd(2) = ddd2(3)
        'ddd(3) = ddd2(4)
        'ent.Coordinates = ddd3
        
        mindist = 999999
        
        
        For i = 0 To UBound(ddd2) Step 3
        
            dist = getDistance(ddd(0), ddd(1), ddd2(i), ddd2(i + 1))
            
            If dist > 0.1 And dist < mindist Then
                ddd(2) = ddd2(i)
                ddd(3) = ddd2(i + 1)
                mindist = dist
            End If
        Next i
    
        ent.Coordinates = ddd
        
        ent.Update
        
        dist = getDistance(ddd(0), ddd(1), ddd(2), ddd(3))
        
        If dist < length Then
            retb = True
        
        Else
            ent.Delete
            retb = False
        End If
    
    Else
        
        ent.Delete
        retb = False
    End If
    
    'Set ent = ThisDrawing.Mode
    
    getRotatedLine = retb


End Function

Function getExtendLineOverpass(entbase As AcadEntity, entSrc As AcadEntity) As Double()

    Dim ddd As Variant
    
    ddd = entSrc.IntersectWith(entbase, acExtendNone)
     
    getExtendLineOverpass = ddd

End Function

Attribute VB_Name = "ClsParkingLot"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private ent As AcadEntity
Private ddd() As Double
Private offset As Double

Function loadEx()
    Dim ss As New ClsSelReal
    Dim ents() As AcadEntity
    Dim ent As AcadLWPolyline
    Dim selec As New clsSelSets
    Dim repeat As Boolean
    Dim dir As String
    
    Dim offsetObj As Variant
    
    Dim size As Integer
    
    
    ents = selectObjs

    If IsArrayEmpty(ents) = True Then
        ThisDrawing.Utility.prompt "선택되지 않았습니다."
        GoTo EndOfFunction
    End If

    offset = ss.selectParkingLotOffset

    size = UBound(ents)
    For i = 0 To size
        Set ent = ents(i)
        
        repeat = True
        
        init ent
        
        Do While (repeat)
        
            repeat = addBothLine
        Loop
        
        ent.Delete
        
        
        'dispose
    Next
    
        
    
EndOfFunction:



    Debug.Print ""


End Function


Function init(e As AcadEntity)

    Set ent = e
    ddd = ent.Coordinates
    
     
    
End Function

Function addBothLine()

    Dim ent2 As AcadEntity
    Dim ent3 As AcadEntity
    
    Dim pe1 As New ClsPolylineParkingEx
    Dim pe2 As New ClsPolylineParkingEx
    
    Dim sp(2) As Double
    Dim ep(2) As Double
    
    Dim x1, y1, x2, y2, rad As Double
    Dim dx As Double
    Dim dy As Double
    
    Dim repeat As Double
    
    Dim spt As AcadPoint
    
    Dim offsetObj As Variant
    
    repeat = True
    
    x1 = ddd(0)
    y1 = ddd(1)
    x2 = ddd(2)
    y2 = ddd(3)
    
    dx = x2 - x1
    dy = y2 - y1
    
    
    sp(0) = ddd(0)
    sp(1) = ddd(1)
    
    rad = getParkingLineRadian(dx, dy)
    
    ep(0) = ddd(0) + offset * Cos(rad)
    ep(1) = ddd(1) + offset * Sin(rad)
    
    offsetObj = ent.offset(-offset)
    Set ent2 = offsetObj(0)
    
    'Set ent2 = ent.Copy
    'Set spt = ThisDrawing.ModelSpace.AddPoint(ep)
    'spt.Rotate sp, PI / 2
    'ent2.Move sp, spt.Coordinates
    'spt.Delete
    
    offsetObj = ent.offset(offset)
    Set ent3 = offsetObj(0)
    
    'Set ent3 = ent.Copy
    'Set spt = ThisDrawing.ModelSpace.AddPoint(ep)
    'spt.Rotate sp, -PI / 2
    'ent3.Move sp, spt.Coordinates
    'spt.Delete
    
    
    repeat = True
    
    pe1.init ent2
    pe1.setLeft
    
    Do While (repeat)
        repeat = pe1.addcrossline
    Loop
    
    pe1.dispose
    
    repeat = True
    
    pe2.init ent3
    pe2.setRight
    
    Do While (repeat)
        repeat = pe2.addcrossline
    Loop

    pe2.dispose

End Function
Function getParkingLineRadian(dx As Double, dy As Double) As Double


    Dim rad As Double
    
        
    If dx = 0 Then
        rad = PI / 2
       
        If dy < 0 Then
            rad = -rad
        End If
        
    Else
        rad = Atn(dy / dx)
        If dx < 0 Then
            rad = PI + rad
        End If
    End If
    
    getParkingLineRadian = rad


End Function

Attribute VB_Name = "ClsPolylineParking"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private ent As AcadEntity
Private ddd() As Double
Private cidx As Integer
Private sidx As Integer
Private eidx As Integer

Private curpos As New clsPoint
Private nextpt As New clsPoint
Private curpt As New clsPoint


Private lastpt As New clsPoint

Private dist As Double
Private width As Double

Private isLeft As Boolean



Function init(e As AcadEntity)

    Set ent = e
    ddd = ent.Coordinates
    
    sidx = 0
    eidx = UBound(ddd)
    
    curpt.x = ddd(0)
    curpt.y = ddd(1)
    
    curpos.x = ddd(0)
    curpos.y = ddd(1)
    
    nextpt.x = ddd(2)
    nextpt.y = ddd(3)
    
    cidx = 4
    
    width = 5
    
    isLeft = True
    
    
End Function


Function setLeft()
    isLeft = True
End Function

Function setRight()
    isLeft = False
End Function

Function setdistance(d As Double)
    dist = d
    
End Function


Function addcrossline() As Boolean

    Dim dx As Double
    Dim dy As Double
    Dim nx As Double
    Dim ny As Double
    Dim distsub As Double
    Dim rad As Double
    Dim ret As Boolean
    
    ret = False
    
    
    If nextpt.x = 0 Or nextpt.y = 0 Then
        addcrossline = ret
        Exit Function
    End If
    
    distsub = getDistance(curpos.x, curpos.y, nextpt.x, nextpt.y)
    
    If distsub > 0 Then
    
    
        dx = nextpt.x - curpos.x
        dy = nextpt.y - curpos.y
        
            
        If dx = 0 Then
            rad = PI / 2
           
            If dy < 0 Then
                rad = -rad
            End If
            
        Else
            rad = Atn(dy / dx)
            If dx < 0 Then
                rad = PI + rad
            End If
        End If
        
        If dy = 0 Then
            If dx > 0 Then
                nx = curpos.x + width
            Else
                nx = curpos.x - width
            End If
        Else
            nx = curpos.x + width * Cos(rad)
        End If
        
        ny = curpos.y + width * Sin(rad)
        
        'addDonutA nx, ny
        
        getRotatedLine curpos.x, curpos.y, nx, ny
        lastpt.x = curpos.x
        lastpt.y = curpos.y
        
        If dy = 0 Then
            If dx > 0 Then
                curpos.x = curpos.x + dist
            Else
                curpos.x = curpos.x - dist
            End If
        Else
            curpos.x = curpos.x + dist * Cos(rad)
        End If
        
        curpos.y = curpos.y + dist * Sin(rad)
        
        ret = True
        
        
        If distsub < dist Then
        
            If cidx < eidx Then
        
                curpt.x = nextpt.x
                curpt.y = nextpt.y
                
                curpos.x = curpt.x
                curpos.y = curpt.y
        
                nextpt.x = ddd(cidx)
                nextpt.y = ddd(cidx + 1)
                
                
                cidx = cidx + 2
         
        
            Else
                nextpt.x = 0
                nextpt.y = 0
            End If
        
        End If
        
        
    Else
    
    End If
    
    
    addcrossline = ret
    
    


End Function


Function dispose()


    ddd(eidx - 1) = lastpt.x
    ddd(eidx) = lastpt.y
    
    'addDonut5 lastpt.x, lastpt.y
    
    ent.Coordinates = ddd
    ent.Update
    

End Function





Function getcurrentposition() As clsPoint

    

    getcurrentposition = curpos

End Function


Function getRotatedLine(x1 As Double, y1 As Double, x2 As Double, y2 As Double) As AcadEntity


    Dim ddd(3) As Double
    Dim basept(2) As Double
    Dim ent As AcadLWPolyline
    
    
    ddd(0) = x1
    ddd(1) = y1
    ddd(2) = x2
    ddd(3) = y2
    
    
    'addDonut5 x1, y1
    'addDonut5 x2, y2
    
    basept(0) = x1
    basept(1) = y1
    
    Set ent = ThisDrawing.ModelSpace.AddLightWeightPolyline(ddd)
    
    If isLeft = True Then
        ent.Rotate basept, PI / 2
    Else
        ent.Rotate basept, -PI / 2
    End If
    
    ent.color = acRed
    Set getRotatedLine = ent
 
    


End Function


Function nextposition() As clsPoint

    




End Function

Attribute VB_Name = "ClsPolylineParkingEx"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private ent As AcadEntity
Private ddd() As Double
Private cidx As Integer
Private sidx As Integer
Private eidx As Integer
Private lidx As Integer

Private curpos As New clsPoint
Private nextpt As New clsPoint
Private curpt As New clsPoint


Private lastpt As New clsPoint

Private dist As Double
Private width As Double
Private rotaterad As Double

Private remaindist As Double

Private isLeft As Boolean




Function load()
    Dim ents() As AcadEntity
    Dim ent As AcadEntity
    Dim selec As New clsSelSets
    Dim repeat As Boolean
    Dim dir As String
    
    Dim size As Integer
    
    
    ents = selectObjs

    If IsArrayEmpty(ents) = True Then
        ThisDrawing.Utility.prompt "선택되지 않았습니다."
        GoTo EndOfFunction
    End If

    dir = ThisDrawing.Utility.GetString(False, "방향(Default: Left): L or R")
    
    size = UBound(ents)
    For i = 0 To size
        Set ent = ents(i)
        
        repeat = True
        
        init ent
        If dir = "R" Or dir = "r" Then
            setRight
        End If
        
        Do While (repeat)
        
            repeat = addcrossline
        
        Loop
        
        dispose
    Next
    
EndOfFunction:
    Debug.Print ""


End Function

 


Function init(e As AcadEntity)

    Dim str() As String
    
    Set ent = e
    ddd = ent.Coordinates
    
    sidx = 0
    eidx = UBound(ddd)
    
    curpt.x = ddd(0)
    curpt.y = ddd(1)
    
    curpos.x = ddd(0)
    curpos.y = ddd(1)
    
    nextpt.x = ddd(2)
    nextpt.y = ddd(3)
    
    cidx = 4
    
    str = getTempSplit
    
    
    dist = CDbl(str(0))
    width = CDbl(str(1))
    
    rotaterad = PI / 2
    
    isLeft = True
    remaindist = 0
    
    'Print ("has arc: " & hasArc(ent))
    
End Function

Private Function hasArc(reg As Variant) As Boolean

    Dim arr As Variant
    Dim size As Integer
    Dim ret As Boolean

    ret = False

    arr = reg.Explode
    size = UBound(arr)
    
    For i = 0 To size
        If TypeOf arr(i) Is AcadArc Then
            arr(i).color = acBlue
            ret = True
            Exit For
        End If
    
    Next
    
    For i = 0 To size
        arr(i).Delete
    
    Next
    
    hasArc = ret

End Function


Function setWidth(d As Double)
    width = d

End Function

Function setParkingLineRotateRadian(r As Double)
    rotaterad = r

End Function


Function setLeft()
    isLeft = True
End Function

Function setRight()
    isLeft = False
End Function

Function setdistance(d As Double)
    dist = d
    
End Function



Function getParkingLineRadian(dx As Double, dy As Double) As Double


    Dim rad As Double
    
        
    If dx = 0 Then
        rad = PI / 2
       
        If dy < 0 Then
            rad = -rad
        End If
        
    Else
        rad = Atn(dy / dx)
        If dx < 0 Then
            rad = PI + rad
        End If
    End If
    
    getParkingLineRadian = rad


End Function

Function addcrossline() As Boolean

    Dim dx As Double
    Dim dy As Double
    Dim nx As Double
    Dim ny As Double
    Dim distsub As Double
    Dim rad As Double
    Dim ret As Boolean
    Dim entsub As AcadEntity
    
    ret = False
        
    If nextpt.x = 0 Or nextpt.y = 0 Then
        addcrossline = ret
        Exit Function
    End If
    
    distsub = getDistance(curpos.x, curpos.y, nextpt.x, nextpt.y)
    
    If distsub > 0 Then
    
    
        dx = nextpt.x - curpos.x
        dy = nextpt.y - curpos.y
        
        rad = getParkingLineRadian(dx, dy)
        
        If dy = 0 Then
            If dx > 0 Then
                nx = curpos.x + width
            Else
                nx = curpos.x - width
            End If
        Else
            nx = curpos.x + width * Cos(rad)
        End If
        
        ny = curpos.y + width * Sin(rad)
        
        'addDonutA nx, ny
        
        getRotatedLine curpos.x, curpos.y, nx, ny
        
        
        lastpt.x = curpos.x
        lastpt.y = curpos.y
        lidx = cidx - 2
        
        
        ret = True
        
        
        If distsub >= dist Then
            If dy = 0 Then
                If dx > 0 Then
                    curpos.x = curpos.x + dist
                Else
                    curpos.x = curpos.x - dist
                End If
            Else
                curpos.x = curpos.x + dist * Cos(rad)
            End If
            
            curpos.y = curpos.y + dist * Sin(rad)
        
        Else
        
            remaindist = 0
        
            Do While (distsub < dist)
            
                If cidx < eidx Then
            
                    curpt.x = nextpt.x
                    curpt.y = nextpt.y
                    
                    nextpt.x = ddd(cidx)
                    nextpt.y = ddd(cidx + 1)
                    
                    cidx = cidx + 2
             
                    remaindist = getDistance(curpt.x, curpt.y, nextpt.x, nextpt.y)
                    If distsub + remaindist >= dist Then
                        
                        dx = nextpt.x - curpt.x
                        dy = nextpt.y - curpt.y
                        
                        rad = getParkingLineRadian(dx, dy)
                        
                        If dy = 0 Then
                            If dx > 0 Then
                                curpos.x = curpt.x + (dist - distsub)
                            Else
                                curpos.x = curpt.x - (dist - distsub)
                            End If
                        Else
                            curpos.x = curpt.x + (dist - distsub) * Cos(rad)
                        End If
                        
                        curpos.y = curpt.y + (dist - distsub) * Sin(rad)
                    End If
                    
                    'addDonut5 curpos.x, curpos.y
                     
                    
                    distsub = distsub + remaindist
             
                    Debug.Print "sub: " & distsub
             
                Else
                    nextpt.x = 0
                    nextpt.y = 0
                    Exit Do
                End If
            
            Loop
            
            'If nextpt.x > 0 And nextpy.y > 0 Then
            
                
            
            'End If
            
        End If
            
        
    Else
    
    End If
    
    
    addcrossline = ret
    
    


End Function

 
Function dispose()

    Dim ddd2() As Double
    Dim idx As Integer
    
    ReDim ddd2(lidx + 1) As Double
    
    For idx = 0 To UBound(ddd2) - 2
        ddd2(idx) = ddd(idx)
    Next
    
    
    
    
    ddd2(idx) = lastpt.x
    ddd2(idx + 1) = lastpt.y
    

    'addDonut5 ddd(lidx), ddd(lidx + 1)

    'ddd(eidx - 1) = lastpt.x
    'ddd(eidx) = lastpt.y
    
    'addDonut5 lastpt.x, lastpt.y
    
    ent.Coordinates = ddd2
    ent.Update
    
    ent.layer = getAddLayerName("RD_SISUL_L_주차장구획선주선_151207")

End Function





Function getcurrentposition() As clsPoint

    

    getcurrentposition = curpos

End Function


Function getRotatedLine(x1 As Double, y1 As Double, x2 As Double, y2 As Double) As AcadEntity


    Dim ddd(3) As Double
    Dim basept(2) As Double
    Dim ent As AcadLWPolyline
    
    
    ddd(0) = x1
    ddd(1) = y1
    ddd(2) = x2
    ddd(3) = y2
    
    
    'addDonut5 x1, y1
    'addDonut5 x2, y2
    
    basept(0) = x1
    basept(1) = y1
    
    Set ent = ThisDrawing.ModelSpace.AddLightWeightPolyline(ddd)
    
    If isLeft = True Then
        ent.Rotate basept, rotaterad
    Else
        ent.Rotate basept, -rotaterad
    End If
    
    'ent.color = acRed
    
    ent.layer = getAddLayerName("RD_SISUL_L_주차장구획선간선_151208")
    
    Set getRotatedLine = ent
 
    


End Function


Function nextposition() As clsPoint

    




End Function

Attribute VB_Name = "ClsPolylineReader"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private polyline As AcadLWPolyline
Private ddd() As Double


Public Function init(ent As AcadLWPolyline)

    Set polyline = ent
    
    ddd = polyline.Coordinates
    

End Function



Public Function getLongDDLine(vx As Double, vy As Double) As Double()

    
    Dim selidx As Integer
    Dim size As Integer
    Dim x As Double
    Dim y As Double
    
    Dim d1() As Double
    Dim d2() As Double
    
    Dim dist1 As Double
    Dim dist2 As Double
    
    selidx = -1
    
    size = UBound(ddd)
    
    For i = 0 To size Step 2
    
        x = ddd(i)
        y = ddd(i + 1)
        
        If isEqualsDouble(x, y, vx, vy) Then
        
            selidx = i
            Exit For
        
        End If
    
    Next i
    
    If selidx >= 0 Then
    
        ReDim dd1(selidx + 1) As Double
        ReDim dd2(size - (selidx + 1) + 1) As Double
    
        For i = 0 To selidx Step 2
            dd1(i) = ddd(i)
            dd1(i + 1) = ddd(i + 1)
        Next i
        
        For i = selidx To size Step 2
        
            dd2(i - selidx) = ddd(i)
            dd2(i - selidx + 1) = ddd(i + 1)
        
        Next i
    
    
    End If
    
    
    
    dist1 = getArrayDistance(dd1)
    dist2 = getArrayDistance(dd2)
    
    
    If dist1 < dist2 Then
        getLongDDLine = dd2
    
    Else
        getLongDDLine = dd1
    
    End If
    
    

End Function

Public Function getLineFromStart(ByVal vv As Double) As Double()

    Dim size As Integer
    Dim dist As Double
    Dim x1, y1, x2, y2 As Double
    Dim rate As Double
    Dim ret(1) As Double
    
    
    size = UBound(ddd)

    x1 = ddd(0)
    y1 = ddd(1)

    For i = 2 To size Step 2
    
        x2 = ddd(i)
        y2 = ddd(i + 1)
        
        dist = getDistance(x1, y1, x2, y2)
        
        If dist > vv Then
        
            rate = vv / dist
            
            
            ret(0) = x1 + (x2 - x1) * rate
            ret(1) = y1 + (y2 - y1) * rate
            
            Exit For
        
        End If
        
        x1 = x2
        y1 = y2
        
        vv = vv - dist
        
    Next i


    getLineFromStart = ret


End Function


Public Function getLineFromEnd(ByVal vv As Double) As Double()

    Dim size As Integer
    Dim dist As Double
    Dim x1, y1, x2, y2 As Double
    Dim rate As Double
    Dim ret(1) As Double
    
    
    size = UBound(ddd)

    x1 = ddd(size - 1)
    y1 = ddd(size)

    For i = size - 3 To 0 Step -2
    
        x2 = ddd(i)
        y2 = ddd(i + 1)
        
        dist = getDistance(x1, y1, x2, y2)
        
        If dist > vv Then
        
            rate = vv / dist
            
            
            ret(0) = x1 + (x2 - x1) * rate
            ret(1) = y1 + (y2 - y1) * rate
            
            Exit For
        
        End If
        x1 = x2
        y1 = y2
        vv = vv - dist
        
    Next i


    getLineFromEnd = ret


End Function

Public Function getLineWingPoint(pts As clsPoint, ptn As clsPoint, r As Double, rad As Double) As Double()


    Dim ptx As New clsPoint
    'Dim dd(3) As Double
    Dim ret(1) As Double
    
    
    ptx.x = pts.x + 5
    ptx.y = pts.y
    
    ang = getAngleEx(pts.x, pts.y, ptx.x, ptx.y, ptn.x, ptn.y)
    ang = ang + rad
    
    'dd(0) = pts.x
    'dd(1) = pts.y
    
    ret(0) = pts.x + r * Math.Cos(ang)
    ret(1) = pts.y + r * Math.Sin(ang)
    
    getLineWingPoint = ret
    


End Function

Attribute VB_Name = "ClsPropLoader"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private dict As New Dictionary





Function load_layer_table(strpath As String)

    Dim fso As Object
    Dim myFileText As String
    Dim arr() As String
    
    Set fso = CreateObject("Scripting.FileSystemObject")
    
    If fso.FileExists(strpath) = False Then
    
        write_file ("여기에 " & strpath & " 파일을 만들어야 합니다")
        MsgBox CurDir$ & "\" & strpath & vbCrLf & "파일을 찾을 수 없습니다."
    
    Else
    
        Dim oFile As Object
        Set oFile = fso.OpenTextFile(strpath, 1) '1: reading, 2: Writing, 3: appending
         
        ' You can also read it line by line
        Dim line As String
        While Not oFile.AtEndOfStream ' while we are not finished reading through the file
            line = oFile.ReadLine
            ' do something with the line...
            
            arr() = Split(line, ",")
            
            dict.add arr(0), arr(1)
            'Debug.Print line
        Wend
        oFile.Close
    
    End If
    
    Set fso = Nothing
    Set oFile = Nothing
End Function

Function load_data(strpath As String) As Boolean

    Dim fso As Object
    Dim myFileText As String
    Dim arr() As String
    Dim bret As Boolean
    Dim size As Integer
    
    bret = False
    
    On Error GoTo toEnd
    
    Set fso = CreateObject("Scripting.FileSystemObject")
    
    If fso.FileExists(strpath) = False Then
    
        write_file ("여기에 " & strpath & " 파일을 만들어야 합니다")
        MsgBox CurDir$ & "\" & strpath & vbCrLf & "파일을 찾을 수 없습니다."
        
    Else
    
        Dim oFile As Object
        Set oFile = fso.OpenTextFile(strpath, 1) '1: reading, 2: Writing, 3: appending
         
        ' You can also read it line by line
        Dim line As String
        While Not oFile.AtEndOfStream ' while we are not finished reading through the file
            line = oFile.ReadLine
            ' do something with the line...
            
            arr() = Split(line, ",")
            
            size = UBound(arr)
            
            If size > 0 Then
                dict.add arr(0), arr(1)
            Else
                dict.add arr(0), arr(0)
            End If
            
            
            
            Debug.Print arr(0) & ", " & dict(arr(0))
            'Debug.Print line
        Wend
        oFile.Close
    
        bret = True
    End If
    
toEnd:
    
    Set fso = Nothing
    Set oFile = Nothing
    
    load_data = bret
    
End Function


Function load_data_4toshp(strpath As String) As Boolean

    Dim fso As Object
    Dim myFileText As String
    Dim arr() As String
    Dim bret As Boolean
    
    bret = False
    
    On Error GoTo toEnd
    
    Set fso = CreateObject("Scripting.FileSystemObject")
    
    If fso.FileExists(strpath) = False Then
    
        write_file ("여기에 " & strpath & " 파일을 만들어야 합니다")
        MsgBox CurDir$ & "\" & strpath & vbCrLf & "파일을 찾을 수 없습니다."
         
    Else
    
        Dim oFile As Object
        Set oFile = fso.OpenTextFile(strpath, 1) '1: reading, 2: Writing, 3: appending
         
        ' You can also read it line by line
        Dim line As String
        While Not oFile.AtEndOfStream ' while we are not finished reading through the file
            line = oFile.ReadLine
            ' do something with the line...
            
            arr() = Split(line, ",")
            
            If startsWith(arr(0), "BG_") Then
                arr(0) = mid(arr(0), 4)
            End If
            
            dict.add arr(0), arr(1)
            
            Debug.Print arr(0) & ", " & dict(arr(0))
            'Debug.Print line
        Wend
        oFile.Close
    
        bret = True
    End If
    
toEnd:
    
    Set fso = Nothing
    Set oFile = Nothing
    
    load_data_4toshp = bret
    
End Function



Function getValue(key As String) As String

    Dim ret As String

    ret = dict(key)

    If ret = "" Then
    
        ret = key
    End If

    getValue = ret

End Function

Function getValueEmpty(key As String) As String

    Dim ret As String

    ret = dict(key)

    getValueEmpty = ret

End Function



Function getKeys() As Variant

    Dim v As Variant
    
    
    getKeys = dict.Keys
    


End Function

Attribute VB_Name = "ClsSelEntity"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Const VK_ESCAPE = &H1B, VK_ENTER = &HD, VK_LBUTTON = &H1
'Declare PtrSafe Function GetAsyncKeyState Lib "user32" (ByVal vKey As Long) As Integer

Public ent As AcadEntity
Public pt As New clsPoint
Public ptd As Variant



Public Function selectPolyline(prompt As String) As Boolean
 

    Dim ret As Boolean
    
    ret = True

   On Error GoTo errControl
    
start:
    ThisDrawing.SetVariable "osmode", 545
    ThisDrawing.Utility.getEntity ent, ptd, prompt
    
errControl:
    
    If Err.Description = "Method 'GetEntity' of object 'IAcadUtility' failed" Then
    
        If CheckKey(VK_ESCAPE) = True Or CheckKey(VK_ENTER) Then
            Debug.Print "End"
            
            ret = False
        Else
            Debug.Print "Resume"
            Resume
        End If
    Else
    
        pt.x = ptd(0)
        pt.y = ptd(1)
    
        Debug.Print ""
        
        
        
    End If
    
    selectPolyline = ret
End Function

Public Function getPointD() As Variant

    getPointD = ptd

End Function


Public Function getMovePoindD(dist As Integer) As Variant

    Dim d(0 To 2) As Double
    d(0) = ptd(0) + 5
    d(1) = ptd(1) - 5
    d(2) = ptd(2)
    
    getMovePoindD = d

End Function





Public Function getEntity() As AcadEntity

    Set getEntity = ent

End Function


Public Function getPoint() As clsPoint

    Set getPoint = pt

End Function

Attribute VB_Name = "ClsSelReal"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False



Public Function selectReal()

    Dim rad As Double

    On Error GoTo errControl

    rad = getDefaultFilletRadius
    rad = ThisDrawing.Utility.GetReal("Radius (default: " & rad & ")   ")
    
    setDefaultFilletRadius rad
    
errControl:
    
    If Err.Description = "User input is a keyword" Then
        rad = getDefaultFilletRadius
    Else
    
    End If
    

    selectReal = rad

End Function


Public Function selectFilletRadius()

    Dim rad As Double

    On Error GoTo errControl

    rad = getDefaultFilletRadius
    rad = ThisDrawing.Utility.GetReal("#Radius (default: " & rad & ")   ")
    
    setDefaultFilletRadius rad
    
errControl:
    
    If Err.Description = "User input is a keyword" Then
        rad = getDefaultFilletRadius
    Else
    
    End If
    

    selectFilletRadius = rad

End Function


Public Function selectChamferDistance()

    Dim dist As Double

    On Error GoTo errControl

    dist = getDefaultChamferDistance
    dist = ThisDrawing.Utility.GetReal("#Distance (default: " & dist & ")   ")
    
    setDefaultChamferDistance dist
    
errControl:
    
    If Err.Description = "User input is a keyword" Then
        dist = getDefaultChamferDistance
        
    Else
    
    End If
    

    selectChamferDistance = dist

End Function


Public Function selectBrLength()

    Dim dist As Double

    On Error GoTo errControl

    dist = getDefaultChamferDistance
    dist = ThisDrawing.Utility.GetReal("#Distance (default: " & dist & ")   ")
    
    setDefaultChamferDistance dist
    
errControl:
    
    If Err.Description = "User input is a keyword" Then
        dist = getDefaultChamferDistance
        
    Else
    
    End If
    

    selectChamferDistance = dist

End Function


Public Function selectParkingLotOffset()

    Dim dist As Double
    Dim str() As String
    Dim defvalue As Double
    
    On Error GoTo errControl

    str = getTempSplit
    
    defvalue = CDbl(str(2)) '0.5 'default
    dist = defvalue
    dist = ThisDrawing.Utility.GetReal("#주차장 offset (default: " & dist & ")   ")
    
     
    
errControl:
    
    If Err.Description = "User input is a keyword" Then
        dist = defvalue
        
    Else
    
    End If
    

    selectParkingLotOffset = dist

End Function

Public Function selectScale(sc As Double) As Double

    Dim rad As Double

    On Error GoTo errControl
 
    sc = ThisDrawing.Utility.GetReal("Scale (default: " & sc & ")   ")
     
    
errControl:
    
    If Err.Description = "User input is a keyword" Then
         
    Else
    
    End If
    

    selectScale = sc

End Function

Attribute VB_Name = "ClsSetSnapAng"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private entref As AcadLWPolyline
Private ddd() As Double
Private retd() As Double
Private pt1 As clsPoint
Private pt2 As clsPoint


Public Function load()

    Dim ok As Boolean
    Dim ss As New clsSelSets
    Dim selec1 As New ClsSelEntity
    Dim pt As Variant
    Dim xx As Double
    Dim yy As Double
    Dim rad As Double

    On Error GoTo EndOfFunction
    Debug.Print "==================START ================="
    
    isEdited = False
    okcnt = 0
    
    Set entref = ss.selectOnePolyline
    
    If entref Is Nothing Then
        ThisDrawing.Utility.prompt "선택 오류가 발생했습니다. 하나만 선택해주세요"
        GoTo EndOfFunction
    End If
    
    ThisDrawing.SetVariable "osmode", 543
    pt = ThisDrawing.Utility.getPoint(, "Enter a point1: ")
    
    ddd = entref.Coordinates
    
    retd = findLineAtPoint(entref, pt(0), pt(1))
    
    'addDonutA retd(0), retd(1)
    'addDonutA retd(2), retd(3)
    
    
    rad = getAngle(retd(0), retd(1), retd(2), retd(3))
    
    
    ThisDrawing.SetVariable "SNAPANG", rad
    
    
EndOfFunction:
    
    

    Debug.Print "DONE"


End Function


Public Function dispose()



    ThisDrawing.SetVariable "SNAPANG", 0

End Function

Attribute VB_Name = "ClsShpExporter"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private dict As Dictionary
Private strprofile As String
Private outpath As String

Private prlayerpath As String
Private proplayer As New ClsPropLoader

Private dicttmptbl As Dictionary

Private idx_active As Integer



Public Function init() As Boolean

    Dim key As Variant
    Dim value As Variant
    Dim pfile As String
    Dim bret As Boolean
    
    bret = True
    
    Set dicttmptbl = New Dictionary
    
    
    pfile = getShpExportLayerPropFile
    
    If pfile <> "" Then
        bret = proplayer.load_data_4toshp(pfile)
    Else
    
        bret = False
    End If
    
    If bret = True Then
    
        'findactivelayer
        Set dict = getBaseLayer
        
        For Each key In dict
            value = dict.Item(key)
            Debug.Print key & "> " & value
            
        Next
        
        outpath = getShpFilePath
    Else
        MsgBox pfile & " 설정파일에 오류가 있습니다"
    End If
    
    init = bret
    
End Function

Public Function initEx() As Boolean

    Dim key As Variant
    Dim value As Variant
    Dim pfile As String
    Dim bret As Boolean
    
    bret = True
    
    Set dicttmptbl = New Dictionary
    
    
    pfile = getShpExportLayer2PropFile
    
    If pfile <> "" Then
        bret = proplayer.load_data(pfile)
    Else
    
        bret = False
    End If
    
    If bret = True Then
    
        findactivelayer
    
        Set dict = getBaseLayerEx
        
        For Each key In dict
            value = dict.Item(key)
            Debug.Print key & "> " & value
            
        Next
        
        outpath = getShpFilePath
    Else
        MsgBox pfile & " 설정파일에 오류가 있습니다"
    End If
    
    initEx = bret
    
End Function

Public Function initEx2() As Boolean

    Dim key As Variant
    Dim value As Variant
    Dim pfile As String
    Dim bret As Boolean
    
    bret = True
    
    Set dicttmptbl = New Dictionary
    
    
    pfile = getShpExportLayer2PropFile
    
    If pfile <> "" Then
        bret = proplayer.load_data(pfile)
        
    Else
    
        bret = False
    End If
    
    If bret = False Then
        MsgBox pfile & " 설정파일에 오류가 있습니다"
    Else
        bret = generate_profile
    End If
    
    
    If bret = False Then
        MsgBox "프로파일을 찾을수 없습니다."
    
    Else
    
        findactivelayer
    
        outpath = getShpFilePath
    
        Set dict = getBaseLayerEx2
         
        
    End If
    
    initEx2 = bret
    
End Function


Public Function generate_profile() As Boolean

    Dim pfile As String
    Dim bret As Boolean
    Dim strsrc As String
    Dim strdst As String
    
    bret = True
    pfile = getProfilePropFile
    
    
    If pfile <> "" Then
    
        strprofile = read_profile(pfile)
        
        Debug.Print strprofile
    Else
    
        bret = False
    End If
    
    
    
    generate_profile = bret

End Function

Public Function exec_profile()

    Dim key As Variant

    
    For Each key In dict
    
        exec_command key, dict.Item(key)
        
    Next

        
        

End Function

Function exec_command(key As Variant, value As String)


    Dim varr() As String
    Dim tblname As String
    Dim layerlist As String
    Dim strdst As String
    
    Dim pfilename As String
    Dim outfile As String
    Dim pfilename2 As String
    Dim shpname As String
    
    Dim shptype As String
    Dim filepath As String

    Dim size As Integer

    shpname = key
    pfilename = getExecProfilePropFile

    Debug.Print shpname & "> " & value
    
    varr() = Split(value, "|")
    size = UBound(varr)
    If size = 0 Then
        'tblname = dicttmptbl.Item(shpname)
        tblname = ""
        layerlist = varr(0)
    
    Else
        tblname = "@" & varr(0)
        layerlist = varr(1)
    End If
    
    shptype = proplayer.getValueEmpty(shpname)
    
    
    If startsWith(shpname, "!!추가") = True Then
        filepath = getShpExtFilePath(outpath, "A")
    
    ElseIf startsWith(shpname, "!!변경") = True Then
        filepath = getShpExtFilePath(outpath, "U")
    ElseIf startsWith(shpname, "!!삭제") = True Then
        filepath = getShpExtFilePath(outpath, "D")
    
    Else
        filepath = outpath
    
    End If
    
    
    
    
    varr() = Split(shptype, "|")
    size = UBound(varr)
    If size > 0 Then
        shptype = varr(0)
        shpname = varr(1)
    End If
    
    
    layerlist = Replace(layerlist, "&", "&amp;")
    
    strdst = Replace(strprofile, "__GEOMTYPE__", shptype)
    strdst = Replace(strdst, "__LAYERLIST__", layerlist)
    strdst = Replace(strdst, "__TABLENAME__", tblname)
    
    write_profile pfilename, strdst
    
    
    
    
    outfile = filepath & "\\" & shpname & ".shp"

    outfile = Replace(outfile, "\", "\\")
    pfilename2 = Replace(pfilename, "\", "\\")

    cmd = "(command ""-mapexport"" ""SHP"" """ & outfile & """ ""Y"" """ & pfilename2 & """ ""Proceed"" )" & vbLf

    ThisDrawing.SendCommand cmd
    
        

End Function


Function read_profile(strpath As String) As String
    Dim objStream As Object
    Set objStream = CreateObject("ADODB.Stream")
    objStream.Open
    objStream.Type = 2 'adTypeText
    objStream.Charset = "UTF-8"
    objStream.LoadFromFile strpath
    TextStrimRead = objStream.ReadText
    Set objStream = Nothing
 
    
    read_profile = TextStrimRead
     
End Function


Function write_profile(strPathName As String, strString As String)
    
    Dim objStream As Object
    Set objStream = CreateObject("ADODB.Stream")
    objStream.Open
    objStream.Type = 2 'adTypeText
    objStream.Charset = "UTF-8"
    objStream.WriteText strString
    objStream.SaveToFile strPathName, 2 'adSaveCreateOverWrite
    Set objStream = Nothing
     
     
End Function


Private Function getBaseLayer() As Dictionary
    Dim actlyr As AcadLayer
    Dim lyr As AcadLayer
    Dim exist As Boolean
    Dim lyrname As String
    Dim lyrkey As String
    Dim idx As Integer
    Dim values As String
    
    Dim ents As Variant
    Dim ent As AcadEntity
    Dim tblname As String
    Dim enttype As String
    
    Dim size As Integer
    Dim tempstr As String
    
    exist = False
    count = ThisDrawing.layers.count
    
    Set dict = New Dictionary
    
    Set actlyr = ThisDrawing.ActiveLayer
    
    For idx = 0 To count - 1
        Set lyr = ThisDrawing.layers.Item(idx)
        lyrname = lyr.name
        lyrkey = Replace(lyrname, "!!추가_", "")
        lyrkey = Replace(lyrkey, "!!변경_", "")
        lyrkey = Replace(lyrkey, "!!삭제_", "")
        
        Debug.Print lyrname & " > " & lyrkey
        
        If lyrname <> lyrkey Then
            
            If startsWith(lyrkey, "BG_") Then
            
                lyrkey = mid(lyrkey, 4)
            
            End If
        
            activeLayerOn lyr, idx
        
            'If actlyr.name = lyrname Then   ' Active layer는 Freeze를 on/off가 막힘.
            
            '    If idx = 0 Then
            '        ThisDrawing.ActiveLayer = ThisDrawing.layers.Item(idx + 1)
            '    Else
            '        ThisDrawing.ActiveLayer = ThisDrawing.layers.Item(idx - 1)
            '    End If
            '
            '    lyr.LayerOn = True
            '    lyr.Freeze = False
            '    lyr.Lock = False
            '
            '    ThisDrawing.ActiveLayer = lyr
           '
            'Else
            '    lyr.LayerOn = True
            '    lyr.Freeze = False
            '    lyr.Lock = False
            'End If
            
            lyrkey = getShpLayer(lyrkey)
            
            'lyrkey = splitLastString(lyrkey, "_")
            
            
            
            enttype = proplayer.getValueEmpty(lyrkey)
            
            If enttype <> "" Then
            
                If dict.exists(lyrkey) = False Then
                
                
                    'ents = selectObjectFromLayers(lyrname)
                    'For i = 0 To UBound(ents)
                    '    Set ent = ents(i)
                        
                    '    tblname = hasTablename(ent)
                        
                    '    If tblname <> "" Then
                        
                    '        Exit For
                    '    End If
                        
                        
                    'Next
                
                    
                    'If tblname <> "" Then
                        'dict.add key:="" & lyrkey, Item:=tblname & "|" & lyrname
                        dict.add key:="" & lyrkey, Item:=lyrname
                    
                    'Else
                    '    Debug.Print lyrname & " 테이블을 찾을 수 없습니다."
                    'End If
                    
                    
                Else
                    values = dict.Item(lyrkey)
                    dict.remove (lyrkey)
                    
                    values = values & "," & lyrname
                    
                    dict.add key:="" & lyrkey, Item:="" & values
                
                End If
                
                
                If startsWith(lyrname, "!!추가") = False Then
                
                    values = dict.Item(lyrkey)
                    
                    If UBound(Split(values, "|")) = 0 Then
                    
                        ents = selectObjectFromLayers(lyrname)
                        For i = 0 To UBound(ents)
                            Set ent = ents(i)
                            
                            tblname = hasTablename(ent)
                            
                            If tblname <> "" Then
                            
                                Exit For
                            End If
                        Next
                        
                        If tblname <> "" Then
                        
                            dict.remove (lyrkey)
                            dict.add key:="" & lyrkey, Item:=tblname & "|" & values
                    
                        End If
                    
                    End If
                    
                
                End If
                
                'setTempLayer lyrname, lyrkey
                
            End If
        End If
        
    Next idx
    
    
    Set getBaseLayer = dict

End Function



Private Function getBaseLayerEx() As Dictionary
    Dim actlyr As AcadLayer
    Dim lyr As AcadLayer
    Dim exist As Boolean
    Dim lyrname As String
    Dim lyrkey As String
    Dim idx As Integer
    Dim values As String
    
    Dim ents As Variant
    Dim ent As AcadEntity
    Dim tblname As String
    Dim enttype As String
    
    Dim size As Integer
    Dim tempstr As String
    Dim key As Variant
    Dim shplyr As String
    
    exist = False
    count = ThisDrawing.layers.count
    
    Set dict = New Dictionary
    
    Set actlyr = ThisDrawing.ActiveLayer
        
        
    For Each key In proplayer.getKeys
        lyrkey = key
        
        'If startsWith(lyrkey, "BG_") Then
        '    lyrkey = mid(lyrkey, 4)
        'End If
        
        For idx = 0 To count - 1
            Set lyr = ThisDrawing.layers.Item(idx)
            lyrname = lyr.name
        
            If startsWith(lyrname, lyrkey) = True Then
                
                activeLayerOn lyr, idx
            
                If dict.exists(lyrkey) = False Then
                    dict.add key:="" & lyrkey, Item:=lyrname
                Else
                    values = dict.Item(lyrkey)
                    dict.remove (lyrkey)
                    
                    values = values & "," & lyrname
                    
                    dict.add key:="" & lyrkey, Item:="" & values
                
                End If
                
                
                values = dict.Item(lyrkey)
                
                If UBound(Split(values, "|")) = 0 Then
                
                    ents = selectObjectFromLayers(lyrname)
                    For i = 0 To UBound(ents)
                        Set ent = ents(i)
                        
                        tblname = hasTablename(ent)
                        
                        If tblname <> "" Then
                        
                            Exit For
                        End If
                    Next
                    
                    If tblname <> "" Then
                    
                        dict.remove (lyrkey)
                        dict.add key:="" & lyrkey, Item:=tblname & "|" & values
                
                    End If
                
                End If
                    
                
                 
            End If
        Next idx
    
    Next key
        
    
    Set getBaseLayerEx = dict

End Function


Private Function getBaseLayerEx2() As Dictionary
    Dim actlyr As AcadLayer
    Dim lyr As AcadLayer
    Dim exist As Boolean
    Dim lyrname As String
    Dim lyrkey As String
    Dim idx As Integer
    Dim values As String
    
    Dim ents As Variant
    Dim ent As AcadEntity
    Dim tblname As String
    Dim enttype As String
    
    Dim size As Integer
    Dim tempstr As String
    Dim key As Variant
    Dim shplyr As String
    
    Dim lyrlist As String
    
    exist = False
    count = ThisDrawing.layers.count
    
    Set dict = New Dictionary
    
    Set actlyr = ThisDrawing.ActiveLayer
        
        
    For Each key In proplayer.getKeys
        lyrkey = key
        
        'If startsWith(lyrkey, "BG_") Then
        '    lyrkey = mid(lyrkey, 4)
        'End If
        
        For idx = 0 To count - 1
            Set lyr = ThisDrawing.layers.Item(idx)
            lyrname = lyr.name
        
            If startsWith(lyrname, lyrkey) = True Then
                
                activeLayerOn lyr, idx
            
                If dict.exists(lyrkey) = False Then
                    dict.add key:="" & lyrkey, Item:=lyrname
                Else
                    values = dict.Item(lyrkey)
                    dict.remove (lyrkey)
                    
                    values = values & "," & lyrname
                    
                    dict.add key:="" & lyrkey, Item:="" & values
                
                End If
                
                
                values = dict.Item(lyrkey)
                
                If UBound(Split(values, "|")) = 0 Then
                
                    tblname = gettablename(lyrname)
                    
                    If tblname <> "" Then
                    
                        dict.remove (lyrkey)
                        dict.add key:="" & lyrkey, Item:=tblname & "|" & values
                
                    End If
                
                End If
                    
                
                 
            End If
        Next idx
        
        
        lyrlist = dict.Item(lyrkey)
        
        If lyrlist <> "" Then
            ThisDrawing.Utility.prompt "작업중: " & lyrkey
            exec_command lyrkey, dict.Item(lyrkey)
        Else
            ThisDrawing.Utility.prompt "작업생략(레이어없음): " & lyrkey
        End If
        
        
    
    Next key
        
    
    Set getBaseLayerEx2 = dict

End Function

Private Function gettablename(lyrname As String) As String

    Dim ent As AcadEntity
    
    Set ent = selectObjectFromLayer(lyrname)
    
    tblname = hasTablename(ent)

    ThisDrawing.Utility.prompt "테이블이름: " & tblname

    gettablename = tblname
    
    
    
    'ents = selectObjectFromLayers(lyrname)
    'For i = 0 To UBound(ents)
    '    Set ent = ents(i)
    '
    '    tblname = hasTablename(ent)
    '
    '    If tblname <> "" Then
    '
    '        Exit For
    '    End If
    'Next

End Function

Private Function findactivelayer()
    Dim count As Integer
    Dim lyr As AcadLayer
    
    count = ThisDrawing.layers.count
    
    For idx = 0 To count - 1
        Set lyr = ThisDrawing.layers.Item(idx)
        
        
        If lyr.LayerOn = True And lyr.Freeze = False And lyr.Lock = False Then
        
            idx_active = idx
            Exit For
        End If
        
    Next
    
    Debug.Print "ACTIVE LAYER IDX: " & idx_active
    
End Function


Private Function activeLayerOn(lyr As AcadLayer, idx As Integer)

    Dim actlyr As AcadLayer
    Dim tmplyr As AcadLayer
    
    Set actlyr = ThisDrawing.ActiveLayer
    

    If actlyr.name = lyr.name Then   ' Active layer는 Freeze를 on/off가 막힘.
            
        If idx = 0 Then
            Set tmplyr = ThisDrawing.layers.Item(idx - 1)
        Else
            Set tmplyr = ThisDrawing.layers.Item(idx - 1)
        End If
        
        tmplyr.LayerOn = True
        tmplyr.Freeze = False
        tmplyr.Lock = False
        ThisDrawing.ActiveLayer = tmplyr
        
        lyr.LayerOn = True
        lyr.Freeze = False
        lyr.Lock = False
        
        ThisDrawing.ActiveLayer = lyr
    
    Else
        lyr.LayerOn = True
        lyr.Freeze = False
        lyr.Lock = False
    End If

End Function




Function getShpLayer(lyr As String) As String

    Dim key As Variant
    Dim shplyr As String
    Dim ret As String
    
    ret = ""
    For Each key In proplayer.getKeys
        shplyr = key
        If startsWith(lyr, shplyr) = True Then
        
            ret = key
            Exit For
        
        End If
    
    Next key
    
    getShpLayer = ret
    
    


End Function

Function setTempLayer(lyrname As String, lyrkey As String)

    Dim values As String
    Dim tblname As String
    Dim ent As AcadEntity

    values = dicttmptbl.Item(lyrkey)
                        
    If values = "" Then
    
        ents = selectObjectFromLayers(lyrname)
        For i = 0 To UBound(ents)
            Set ent = ents(i)
            
            tblname = hasTablename(ent)
            
            If tblname <> "" Then
            
                Exit For
            End If
        Next
        
        If tblname <> "" Then
            dicttmptbl.remove (lyrkey)
            dicttmptbl.add key:="" & lyrkey, Item:=tblname
    
        End If
    
    End If
End Function

Attribute VB_Name = "ClsSplitPolyline"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private srcents As Variant
Private pg As AcadLWPolyline
Private pl As AcadLWPolyline
Private tmp As AcadLWPolyline
Private ddd() As Double
Private retd(7) As Double
Private retent As AcadLWPolyline
Private retreg As AcadRegion


Private retreg1 As AcadRegion
Private retreg2 As AcadRegion

Private retent1 As AcadLWPolyline
Private retent2 As AcadLWPolyline

Private layername As String




Function load()


    Dim x1, y1, x2, y2 As Double
    Dim r As Double
    Dim rad As Double
    Dim dx As Double
    Dim dy As Double
    Dim dist As Double
    Dim ents() As AcadEntity
    Dim regs() As AcadRegion
 
    
    rad = (PI / 2) * 99 / 100
    dist = 0.1
    
    srcents = selectPLObjs
    
    If UBound(srcents) = 1 Then
    
        Set tmp = srcents(0)
        
        If tmp.Closed = True Then
            Set pg = tmp
            
            If srcents(1).Closed = False Then
                Set pl = srcents(1)
            End If
            
        Else
        
            Set pl = tmp
            If srcents(1).Closed = True Then
                Set pg = srcents(1)
            
            End If
           
        End If
        
        layername = pg.layer
        
        'pg <> None And pl <> None Then
        
        If TypeOf pg Is AcadLWPolyline And TypeOf pl Is AcadLWPolyline Then
        
            ddd = pl.Coordinates
            
            x1 = ddd(0)
            y1 = ddd(1)
            x2 = ddd(2)
            y2 = ddd(3)
            
            retd(0) = x1
            retd(1) = y1
            retd(2) = x2
            retd(3) = y2
            
            
            r = getDistance(x1, y1, x2, y2)
            rad = getRadian(x2 - x1, y2 - y1)
            
            rad = rad + PI / 2
            
            dx = dist * Cos(rad)
            dy = dist * Sin(rad)
            
            retd(4) = x2 + dx
            retd(5) = y2 + dy
            
            'addDonutA retd(4), retd(5)
            
            retd(6) = x1 + dx
            retd(7) = y1 + dy
            
            'addDonutA retd(6), retd(7)
            
            
            Set retent = ThisDrawing.ModelSpace.AddLightWeightPolyline(retd)
            retent.Closed = True
            
            setRegionIntersect
            setRegionSubtraction
            
            retent.Delete
    
            splitRegions
    
            
            Debug.Print ""
            
            pl.Delete
            
        
            If layername = "0" Then
            
                pg.Delete
            Else
                pg.layer = getDelLayerName(layername)
            End If
        
        End If
        
    
    
    End If
    

End Function

Function setRegionIntersect()
    Dim reg1 As AcadRegion
    Dim reg2 As AcadRegion
    
    Dim ents(0) As AcadEntity
            
    Set ents(0) = pg
    regs = ThisDrawing.ModelSpace.AddRegion(ents)
    Set reg1 = regs(0)
    
    Set ents(0) = retent
    regs = ThisDrawing.ModelSpace.AddRegion(ents)
    Set reg2 = regs(0)
    
    reg2.Boolean acIntersection, reg1
    
    Set retreg2 = reg2

End Function

Function setRegionSubtraction()
    Dim reg1 As AcadRegion
    Dim reg2 As AcadRegion
    
    Dim ents(0) As AcadEntity
            
    Set ents(0) = pg
    regs = ThisDrawing.ModelSpace.AddRegion(ents)
    Set reg1 = regs(0)
    
    Set ents(0) = retent
    regs = ThisDrawing.ModelSpace.AddRegion(ents)
    Set reg2 = regs(0)
    
    reg1.Boolean acSubtraction, reg2
    
    Set retreg1 = reg1

End Function



Function splitRegions()

    Dim arr As Variant
    Dim subreg1 As AcadRegion
    Dim subreg2 As AcadRegion
    
    Dim resent1 As AcadEntity
    Dim resent2 As AcadEntity
    
    arr = retreg1.Explode
    size = UBound(arr)
        
    
    Set subreg1 = arr(0)
    Set subreg2 = arr(1)
        
    subreg1.Boolean acUnion, retreg2
    
    
    Set resent1 = expoldeRegion(subreg1)(0)
    Set resent2 = expoldeRegion(subreg2)(0)
    
    resent1.layer = getAddLayerName(layername)
    resent2.layer = getAddLayerName(layername)
    
    retreg1.Delete
    
    
        
    Debug.Print ""
        

End Function




Function getGrade(x1 As Double, y1 As Double, x2 As Double, y2 As Double) As Double

    Dim ret As Double
    
    
    ret = (y2 - y1) / (x2 - x1)
    
    getGrade = ret

End Function

Function getRadian(dx As Double, dy As Double) As Double


    Dim rad As Double
    
        
    If dx = 0 Then
        rad = PI / 2
       
        If dy < 0 Then
            rad = -rad
        End If
        
    Else
        rad = Atn(dy / dx)
        If dx < 0 Then
            rad = PI + rad
        End If
    End If
    
    getRadian = rad


End Function

Attribute VB_Name = "ClsTextCreator"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private layername As String
Private layercode As String

Private prloader As New ClsPropLoader

Function load()
 
    Dim ent As AcadLWPolyline
    Dim ents() As AcadEntity
    Dim cnt As Integer
    
    Dim reg As AcadRegion
    
    ents = selectPLObjs
    
    cnt = UBound(ents)
    
    Dim vv() As String
    Dim size As Integer
    Dim value As String
 
    Dim prfile As String
    Dim bret As Boolean
    
    
    prfile = getNcodeSec2PropFile
 
    
    If prfile <> "" Then
    
        prloader.load_data prfile
    
        For i = 0 To cnt
            Set ent = ents(i)
            Set reg = polyline2region(ent)
        
            If reg Is Nothing Then
                
                'addDonutCheck ent.Coordinates(0), ent.Coordinates(1)
                
            Else
            
                layercode = get_layercode(ent)
                value = prloader.getValueEmpty(layercode)
                If value <> "" Then
                            
                    layername = getAddLayerName("POI_" & value & "_" + layercode)
                    
                    create_text reg, layername, value
                    
                End If
            
            
            End If
        Next i
    End If
    

End Function



Function loadEx()
 

    Dim entpl As AcadLWPolyline
    Dim enttxt As AcadText
    
    Dim ents() As AcadEntity
    Dim cnt As Integer
    
    Dim reg As AcadRegion
    
    ents = selectObjs
     
    
    Dim vv() As String
    Dim size As Integer
    Dim value As String
 
    Dim prfile As String
    Dim bret As Boolean
    
    
    prfile = getNcodeSec2PropFile
    bret = False
 
    
    cnt = UBound(ents)
    
    If prfile = "" Or cnt <> 1 Then
        Exit Function
        
    End If
    
    
    prloader.load_data prfile

 
    If TypeOf ents(0) Is AcadLWPolyline And TypeOf ents(1) Is AcadText Then
    
        Set entpl = ents(0)
        Set enttxt = ents(1)
        bret = True
    ElseIf TypeOf ents(1) Is AcadLWPolyline And TypeOf ents(0) Is AcadText Then
    
        Set entpl = ents(1)
        Set enttxt = ents(0)
        bret = True
    End If
    

    If bret = False Then
    
        Exit Function
    End If
    
    Set reg = polyline2region(entpl)

    If reg Is Nothing Then
       
    Else
    
        layercode = get_layercode(entpl)
        value = prloader.getValueEmpty(layercode)
        
        If value <> "" Then
                    
            vv() = Split(value, "|")
        
            size = UBound(vv)
            If size = 1 Then
                layername = getAddLayerName("POI_" & vv(0) & "&" & vv(1))
                
                create_text reg, layername, enttxt.textString & "&" & vv(0)
            End If
        End If
         
    End If

End Function


Function loadEx2()
    Dim ent As AcadLWPolyline
    Dim ents() As AcadEntity
    Dim cnt As Integer
    
    Dim reg As AcadRegion
    
    ents = selectPLObjs
    
    cnt = UBound(ents)
    
    Dim vv() As String
    Dim size As Integer
    Dim value As String
 
    Dim bret As Boolean
 
    
    For i = 0 To cnt
        Set ent = ents(i)
        
        layername = ent.layer
        
        If startsWith(layername, "!!") = True Then
        
            Set reg = polyline2region(ent)
        
            If reg Is Nothing Then
                
                'addDonutCheck ent.Coordinates(0), ent.Coordinates(1)
                
            Else
            
                vv() = Split(layername, "&")
            
                If UBound(vv) >= 2 Then
            
                    layername = getAddLayerName(vv(0) & "&" & vv(1) & "&" & "POI_DB_P")
                    
                    create_text reg, layername, "<입력>"
                    
                End If
            
            
            End If
        
        End If
    Next i
  
End Function


Private Function get_layercode(ent As AcadLWPolyline) As String

    Dim layername As String
    Dim vv() As String
    Dim size As Integer
    Dim layercode As String
    
    layername = ent.layer
            
    vv() = Split(layername, "_")
            
    size = UBound(vv)
    layercode = vv(size)
        
    
            
    get_layercode = layercode

End Function

Private Function get_codevalue(ent As AcadLWPolyline) As String()

    Dim layername As String
    Dim vv() As String
    Dim size As Integer
    Dim layercode As String
    
    layername = ent.layer
            
    vv() = Split(layername, "_")
            
    size = UBound(vv)
    layercode = vv(size)
        
    value = prloader.getValueEmpty(layercode)
            
    ReDim vv(0) As String
    
    If value <> "" Then
                    
        vv() = Split(value, "|")
        
        'layername = getAddLayerName("POI_" & vv(0) & "&" & vv(1))
        
        'create_text reg, layername, enttxt.textString & "&" & vv(0)
                    
    End If
    
    get_codevalue = vv
    

End Function

Private Function create_text(reg As AcadRegion, layername As String, textString As String)

    Dim cent As Variant
    Dim pt(2) As Double
    Dim textObj As AcadText
    
    cent = reg.Centroid
            
    pt(0) = cent(0)
    pt(1) = cent(1)
    
    
    Set textObj = ThisDrawing.ModelSpace.AddText(value, pt, 2)
    textObj.Alignment = acAlignmentMiddleCenter
    textObj.TextAlignmentPoint = pt
    textObj.layer = layername
    textObj.textString = textString
     
    reg.Delete
End Function

Attribute VB_Name = "ClsTextRotater"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private osmd As Integer
Private prop As New ClsPropLoader

Function rotateHatch()


    Dim ha As AcadHatch
    Dim ss As New clsSelSets
    Dim ent As AcadEntity
    Dim msg As String
    
    Dim pt1 As Variant
    Dim pt2 As Variant
    
    Dim rad As Double
    Dim sc As Double
    Dim pfile As String
    
    Dim strangle As String
    Dim baseangle As Double
    
    pfile = getHatchPatternAnglePropFile
    
    If pfile <> "" Then
        bret = prop.load_data(pfile)
    End If
    
    Dim selec As New ClsSelReal
    
    Set ha = ss.selectAnything
    
    baseangle = 0
    
    If bret = True Then
        strangle = prop.getValueEmpty(ha.PatternName)
        
        
        If strangle <> "" Then
            baseangle = CDbl(strangle)
               
            baseangle = DegreesToRadians(baseangle)
        End If
    End If
    
    msg = "Angle: " & ha.PatternAngle & ", scale: " & ha.PatternScale
    
    
    ThisDrawing.SetVariable "osmode", 512
    pt1 = ThisDrawing.Utility.getPoint(, "Get point1: ")
    pt2 = ThisDrawing.Utility.getPoint(, "Get point2: ")
    
    
    sc = selec.selectScale(ha.PatternScale)
    
    rad = getAngle(pt1(0), pt1(1), pt2(0), pt2(1))
    Debug.Print "angle: " & rad
 
    rad = rad + baseangle
    If rad < 0 Then
    
        'Do While (rad < 0)
        
        '    rad = rad + PI / 2
        
        'Loop
    
    Else
        Do While (rad > PI)
        
            rad = rad - PI / 2
        
        Loop
    End If
    
    
    Debug.Print "angle: " & rad
    
    ha.PatternAngle = rad
    ha.PatternScale = sc
    
    ha.Update
    
    Debug.Print msg
    
    'ha.Update
    
    

End Function



Function savemode()

    osmd = ThisDrawing.GetVariable("osmode")


End Function

Function restoremode()
    ThisDrawing.SetVariable "osmode", osmd
    
End Function



Function rotateText()


    Dim ha As AcadText
    Dim ss As New clsSelSets
    Dim ent As AcadEntity
    Dim msg As String
    
    Dim pt1 As Variant
    Dim pt2 As Variant
    
    Dim rad As Double
    Dim sc As Double
    
    
    
    
    Dim selec As New ClsSelReal
    
    Set ha = ss.selectAnything
     
    msg = "Angle: " & ha.Rotation & ", scale: " & ha.ScaleFactor
    
    
    savemode
    
    ThisDrawing.SetVariable "osmode", 545
    pt1 = ThisDrawing.Utility.getPoint(, "Get point1: ")
    pt2 = ThisDrawing.Utility.getPoint(, "Get point2: ")
    
    
    'sc = selec.selectScale(ha.ScaleFactor)
    
    rad = getAngle(pt1(0), pt1(1), pt2(0), pt2(1))
    Debug.Print "angle: " & rad
    
    If rad < 0 Then
    
        'Do While (rad < 0)
        
        '    rad = rad + PI / 2
        
        'Loop
    
    Else
        Do While (rad > PI)
        
            rad = rad - PI / 2
        
        Loop
    End If
    
    
    Debug.Print "angle: " & rad
    
    ha.Rotation = rad
    'ha.ScaleFactor = sc
    
    ha.Update
    
    Debug.Print msg
    
    'ha.Update
    
    restoremode

End Function

Attribute VB_Name = "ClsTunnel"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private isTest As Boolean

'"RD_SISUL_A_주요터널입구_170404|RD_SISUL_A_주요터널마킹_170405|RD_SISUL_L_주요터널히든선_170407"
Private lyrname_entrance As String
Private lyrname_marking As String
Private lyrname_hiddenline As String
 
Private ss As New clsSelSets
Private widthd As Double

Private ent As AcadEntity
    
    
Private pl1 As AcadEntity
Private pl2 As AcadEntity
    
Private ptd1() As Double
Private ptd2() As Double
Private ptd3() As Double
Private ptd4() As Double


Private line1dd() As Double
Private line2dd() As Double


Private ptd5() As Double
Private ptd6() As Double
Private ptd7() As Double
Private ptd8() As Double

Private ptd9() As Double
Private ptd10() As Double
Private ptd11() As Double
Private ptd12() As Double

Private ptd13() As Double
Private ptd14() As Double
Private ptd15() As Double
Private ptd16() As Double


Private pt1 As New clsPoint
Private pt2 As New clsPoint
Private pt3 As New clsPoint
Private pt4 As New clsPoint
    
Private pt5 As New clsPoint
Private pt6 As New clsPoint
Private pt7 As New clsPoint
Private pt8 As New clsPoint

Private pt9 As New clsPoint
Private pt10 As New clsPoint
Private pt11 As New clsPoint
Private pt12 As New clsPoint
    
Private pt13 As New clsPoint
Private pt14 As New clsPoint
Private pt15 As New clsPoint
Private pt16 As New clsPoint
    

Private rad As Double
Private dist1 As Double
Private dist2 As Double
 
Private tun1 As AcadEntity
Private tun2 As AcadEntity



Function setLayers(layers() As String)

    lyrname_entrance = layers(0)
    lyrname_marking = layers(1)
    lyrname_hiddenline = layers(2)
    
    'If lyrname_entrance Like "*주요*" Then
    '    dist1 = 3
    '    dist2 = 6.5
    '    rad = PI / 8
    'Else
    '    dist1 = 0.8
    '    dist2 = 1.72
    '    rad = PI / 10
    'End If
    
    
End Function

Function setdistance(d1 As Double, d2 As Double)

    dist1 = d1
    dist2 = d2

End Function

Function loadEx2()

    Dim layers() As String
    Dim lyrs(2) As String
    Dim selec As New ClsSelEntity

    Dim pr As New clsPolygonReader
    Dim plr As New ClsPolylineReader
    
    Dim pttd(2) As Double
    Dim ptt As New clsPoint
    
    Dim tmpptd() As Double

    On Error GoTo EndOfFunction
    Debug.Print "==================START ================="
    
    isTest = False
    
    'dist1 = 3.5
    'dist2 = 7.5
    'dist1 = 1.04
    'dist2 = 2.22
    
    
    Set ent = ss.selectPolyline
    If ent.Closed = False Then
        ThisDrawing.Utility.prompt "Polyline을 잘못 선택했습니다."
        GoTo EndOfFunction
    End If
        
    
    ThisDrawing.SetVariable "osmode", 544
    
    If isTest = False Then
        'selec.selectPolyline ("Enter a point 1")
        'Set ent = selec.getEntity
        'ptd1 = selec.getPointD
        
        'ptd1 = addVertex2(ent, ptd1(0), ptd1(1))
        
        ptd1 = ThisDrawing.Utility.getPoint(, "Enter a point1: ")
        'ptd2 = ThisDrawing.Utility.getPoint(, "Enter a point2: ")
        ptd3 = ThisDrawing.Utility.getPoint(, "Enter a point3: ")
        'ptd4 = ThisDrawing.Utility.getPoint(, "Enter a point4: ")
        
        'ptd1(0) = 222.808064798255
        'ptd1(1) = 613.404363855576
        'ptd3(0) = 322.417996325084
        'ptd3(1) = 600.936846717623
        
        Debug.Print "ptd1(0) = " & ptd1(0)
        Debug.Print "ptd1(1) = " & ptd1(1)
        Debug.Print "ptd3(0) = " & ptd3(0)
        Debug.Print "ptd3(1) = " & ptd3(1)
        
        tmpptd = selectCrossPoints(ent, ptd1)
        ptd1(0) = tmpptd(0)
        ptd1(1) = tmpptd(1)
        
        ReDim ptd2(2) As Double
        ptd2(0) = tmpptd(2)
        ptd2(1) = tmpptd(3)
        
        tmpptd = selectCrossPoints(ent, ptd3)
        ptd3(0) = tmpptd(0)
        ptd3(1) = tmpptd(1)
        
        ReDim ptd4(2) As Double
        ptd4(0) = tmpptd(2)
        ptd4(1) = tmpptd(3)
        
        
        'addDonutA ptd1(0), ptd1(1)
        'addDonutA ptd2(0), ptd2(1)
        'addDonutA ptd3(0), ptd3(1)
        'addDonutA ptd4(0), ptd4(1)
        
        
    Else
        ReDim ptd1(1) As Double
        ReDim ptd2(1) As Double
        ReDim ptd3(1) As Double
        ReDim ptd4(1) As Double
         
ptd1(0) = 1106581.090286
ptd1(1) = 1688864.14762994
ptd2(0) = 1106581.65407904
ptd2(1) = 1688857.17037135
ptd3(0) = 1106590.27066761
ptd3(1) = 1688857.86662943
ptd4(0) = 1106589.73937065
ptd4(1) = 1688864.84587558
    
    End If
    
    
    Debug.Print "ptd1(0) = " & ptd1(0)
    Debug.Print "ptd1(1) = " & ptd1(1)
    Debug.Print "ptd2(0) = " & ptd2(0)
    Debug.Print "ptd2(1) = " & ptd2(1)
    Debug.Print "ptd3(0) = " & ptd3(0)
    Debug.Print "ptd3(1) = " & ptd3(1)
    Debug.Print "ptd4(0) = " & ptd4(0)
    Debug.Print "ptd4(1) = " & ptd4(1)



    addVertex ent, ptd1(0), ptd1(1)
    addVertex ent, ptd2(0), ptd2(1)
    addVertex ent, ptd3(0), ptd3(1)
    addVertex ent, ptd4(0), ptd4(1)


    pt1.initPt ptd1
    pt2.initPt ptd2
    pt3.initPt ptd3
    pt4.initPt ptd4
    
    
    widthd = getDistance(pt1.x, pt1.y, pt2.x, pt2.y)
    
    layers = getDefaultTunnelLayers
    
    
    
    'If widthd < 10.5 Then
    If ent.layer Like "*171201" Or ent.layer Like "*171202" Then
        
        '주요
        
        'lyrs(0) = "RD_SISUL_A_주요터널입구_170404"
        'lyrs(1) = "RD_SISUL_A_주요터널마킹_170405"
        'lyrs(2) = "RD_SISUL_L_주요터널히든선_170407"
                
        lyrs(0) = layers(3)
        lyrs(1) = layers(4)
        lyrs(2) = layers(5)
        
        
        setLayers lyrs
    Else
        '일반
        
        'lyrs(0) = "RD_SISUL_A_일반터널입구_170403"
        'lyrs(1) = "RD_SISUL_A_일반터널마킹_170406"
        'lyrs(2) = "RD_SISUL_L_일반터널히든선_170408"

        lyrs(0) = layers(0)
        lyrs(1) = layers(1)
        lyrs(2) = layers(2)
        
        setLayers lyrs
    End If
    
            
    If widthd >= 9.9 Then       '10보다 크면인데... 곡선구간은 오차가 있음
        dist1 = 3
        dist2 = 6.5
        rad = PI / 8
    Else
        'dist1 = 0.8
        'dist2 = 1.72
        'rad = PI / 10
        dist1 = 1.5
        dist2 = 3.1544
        rad = PI / 10
    End If
    
    
    '위치 변경
    
    pttd(0) = ptd4(0)
    pttd(1) = ptd4(1)
    
    ptd4(0) = ptd1(0)
    ptd4(1) = ptd1(1)
    ptd1(0) = ptd2(0)
    ptd1(1) = ptd2(1)
    ptd2(0) = ptd3(0)
    ptd2(1) = ptd3(1)
    ptd3(0) = pttd(0)
    ptd3(1) = pttd(1)
    
    
    ptt.x = pt4.x
    ptt.y = pt4.y
    pt4.x = pt1.x
    pt4.y = pt1.y
    pt1.x = pt2.x
    pt1.y = pt2.y
    pt2.x = pt3.x
    pt2.y = pt3.y
    pt3.x = ptt.x
    pt3.y = ptt.y
    

    pr.init ent
    pr.setIndexByPoint pt1
    pr.setEIndexByPoint pt2
    
    line1dd = pr.getShortLine2
    
    pr.setIndexByPoint pt3
    pr.setEIndexByPoint pt4
    
    line2dd = pr.getShortLine2
    
    
    Set pl1 = ThisDrawing.ModelSpace.AddLightWeightPolyline(line1dd)
    Set pl2 = ThisDrawing.ModelSpace.AddLightWeightPolyline(line2dd)
    

    plr.init pl1
    ptd5 = plr.getLineFromStart(dist1)
    ptd6 = plr.getLineFromEnd(dist1)
    
    addVertex ent, ptd5(0), ptd5(1)
    addVertex ent, ptd6(0), ptd6(1)
    
    pt5.initPt ptd5
    pt6.initPt ptd6

    addDonut ptd5(0), ptd5(1)
    addDonut ptd6(0), ptd6(1)
    
    
    ptd7 = plr.getLineWingPoint(pt1, pt5, dist2, -rad)
    ptd8 = plr.getLineWingPoint(pt2, pt6, dist2, rad)
    
    pt7.initPt ptd7
    pt8.initPt ptd8
    
    addDonut ptd7(0), ptd7(1)
    addDonut ptd8(0), ptd8(1)
    
    plr.init pl2
    ptd9 = plr.getLineFromStart(dist1)
    ptd10 = plr.getLineFromEnd(dist1)
    
    addVertex ent, ptd9(0), ptd9(1)
    addVertex ent, ptd10(0), ptd10(1)
    
    addDonut ptd9(0), ptd9(1)
    addDonut ptd10(0), ptd10(1)
     
    pt9.initPt ptd9
    pt10.initPt ptd10
    
    ptd11 = plr.getLineWingPoint(pt3, pt9, dist2, -rad)
    ptd12 = plr.getLineWingPoint(pt4, pt10, dist2, rad)

    pt11.initPt ptd11
    pt12.initPt ptd12
    
    
    setCrossPoint
    
    setTunnel
    

    addDonut ptd11(0), ptd11(1)
    addDonut ptd12(0), ptd12(1)

    setTunIn
    setTunOut
    
     pl1.Delete
    pl2.Delete
EndOfFunction:
    
   
    

    Debug.Print "DONE"
    
    
    
End Function


Private Function setCrossPoint()

    Dim line1 As AcadLine
    Dim line2 As AcadLine
    Dim sp(0 To 2) As Double
    Dim ep(0 To 2) As Double
    Dim inters As Variant


    sp(0) = ptd7(0)
    sp(1) = ptd7(1)
    ep(0) = ptd12(0)
    ep(1) = ptd12(1)

    Set line1 = ThisDrawing.ModelSpace.addLine(sp, ep)
    line1.color = acRed
    
    sp(0) = ptd8(0)
    sp(1) = ptd8(1)
    ep(0) = ptd11(0)
    ep(1) = ptd11(1)

    Set line2 = ThisDrawing.ModelSpace.addLine(sp, ep)
    line2.color = acRed
    
    inters = pl1.IntersectWith(line1, acExtendNone)
    
    ptd13 = addVertexH(pl1, inters(0), inters(1))
    pt13.initPt ptd13
    
    inters = pl2.IntersectWith(line1, acExtendNone)
    ptd14 = addVertexH(pl2, inters(0), inters(1))
    pt14.initPt ptd14
    
    inters = pl1.IntersectWith(line2, acExtendNone)
    ptd15 = addVertexH(pl1, inters(0), inters(1))
    pt15.initPt ptd15
    
    inters = pl2.IntersectWith(line2, acExtendNone)
    ptd16 = addVertexH(pl2, inters(0), inters(1))
    pt16.initPt ptd16
    
    addDonut ptd13(0), ptd13(1)
    addDonut ptd14(0), ptd14(1)
    addDonut ptd15(0), ptd15(1)
    addDonut ptd16(0), ptd16(1)
    
    Debug.Print ""
    line1.Delete
    line2.Delete
    
    

End Function



Public Function setTunnel()
   Dim tmp(13) As Double
   Dim pr1 As New clsPolygonReader
   Dim pr2 As New clsPolygonReader
    Dim ddd1() As Double
    Dim ddd2() As Double
    Dim merge As New ClsMerger
    Dim size As Integer
    Dim ll1(3) As Double
    Dim ll2(3) As Double
    Dim ent As AcadEntity
    Dim hline1 As AcadEntity
    Dim hline2 As AcadEntity
   
   Dim tmp1 As AcadEntity
   Dim tmp2 As AcadEntity
   
   pr1.init pl1
   pr1.setIndexByPoint pt13
   pr1.setEIndexByPoint pt15
   
   
   'addDonutA pt13.x, pt13.y
   'addDonutA pt15.x, pt15.y
   
   pr1.setIndex 0
   
   ddd1 = pr1.getShortLine2Half()
   
   
   pr2.init pl2
   pr2.setIndexByPoint pt16
   pr2.setEIndexByPoint pt14
   
   ddd2 = pr2.getShortLine2Half()
  
  
    pl1.color = acRed
    pl2.color = acRed
  
    'Set tmp1 = ThisDrawing.ModelSpace.AddLightWeightPolyline(ddd1)
    'tmp1.color = acGreen
    'Set tmp2 = ThisDrawing.ModelSpace.AddLightWeightPolyline(ddd2)
    'tmp2.color = acGreen
  
   ll1(0) = ptd13(0)
   ll1(1) = ptd13(1)
   ll1(2) = ptd14(0)
   ll1(3) = ptd14(1)
   
   ll2(0) = ptd15(0)
   ll2(1) = ptd15(1)
   ll2(2) = ptd16(0)
   ll2(3) = ptd16(1)
   
   size = UBound(ddd1) + UBound(ddd2) + UBound(ll1) + UBound(ll2) + 3
   
   merge.setSize size
   merge.add ddd1
   merge.add ll2
   merge.add ddd2
   merge.add ll1
   
   Set ent = ThisDrawing.ModelSpace.AddLightWeightPolyline(merge.getMerged())
   ent.Closed = True
   ent.layer = getAddLayerName(lyrname_marking)
   
   
   Set hline1 = ThisDrawing.ModelSpace.AddLightWeightPolyline(ddd1)
   hline1.layer = getAddLayerName(lyrname_hiddenline)
   Set hline2 = ThisDrawing.ModelSpace.AddLightWeightPolyline(ddd2)
   hline2.layer = getAddLayerName(lyrname_hiddenline)
   
   Debug.Print ""
    
    
    
End Function

Public Function setTunIn()
    Dim tmp(13) As Double
    
    tmp(0) = pt1.x
    tmp(1) = pt1.y
    tmp(2) = pt7.x
    tmp(3) = pt7.y
    tmp(4) = pt12.x
    tmp(5) = pt12.y
    tmp(6) = pt4.x
    tmp(7) = pt4.y
    tmp(8) = pt10.x
    tmp(9) = pt10.y
    tmp(10) = pt5.x
    tmp(11) = pt5.y
    tmp(12) = pt1.x
    tmp(13) = pt1.y
    
    Set tun1 = ThisDrawing.ModelSpace.AddLightWeightPolyline(tmp)
    tun1.Closed = True
    tun1.layer = getAddLayerName(lyrname_entrance)
    
    
End Function

Public Function setTunOut()
    Dim tmp(13) As Double
    
    tmp(0) = pt2.x
    tmp(1) = pt2.y
    tmp(2) = pt8.x
    tmp(3) = pt8.y
    tmp(4) = pt11.x
    tmp(5) = pt11.y
    tmp(6) = pt3.x
    tmp(7) = pt3.y
    tmp(8) = pt9.x
    tmp(9) = pt9.y
    tmp(10) = pt6.x
    tmp(11) = pt6.y
    tmp(12) = pt2.x
    tmp(13) = pt2.y
    
    Set tun2 = ThisDrawing.ModelSpace.AddLightWeightPolyline(tmp)
    tun2.Closed = True
    tun2.layer = getAddLayerName(lyrname_entrance)
    
End Function

Public Function selectCrossPoints(ent As AcadEntity, ptd1() As Double) As Double()

    Dim selec As New clsSelSets
    Dim pt1 As New clsPoint
    Dim ptprev As New clsPoint
    Dim ptnext As New clsPoint
    Dim pr As New clsPolygonReader
    Dim alpha As Double
    Dim ddd(3) As Double
    Dim dddd() As Double
    Dim retd() As Double
    Dim crossline As AcadEntity
    Dim intersd() As Double
    
    ptd1 = addVertex(ent, ptd1(0), ptd1(1))
    
    pt1.initPt ptd1
    
    pr.init ent
    pr.setIndexByPoint pt1
    pr.setIndex pr.getSIndex
    
    addDonut pt1.x, pt1.y
    
    Set ptprev = pr.prevPoint
    Set ptnext = pr.nextPoint
    Set ptnext = pr.nextPoint
    
    ddd(0) = ptprev.x
    ddd(1) = ptprev.y
    ddd(2) = ptnext.x
    ddd(3) = ptnext.y
    
    Set crossline = ThisDrawing.ModelSpace.AddLightWeightPolyline(ddd)
    crossline.color = acRed
    
    
    ReDim ptd1(2) As Double
    ptd1(0) = pt1.x
    ptd1(1) = pt1.y
    crossline.Rotate ptd1, PI / 2
    
    dddd = crossline.Coordinates
    crossline.Delete    '라인 삭제
    
    Set crossline = extendLineBoth(dddd(0), dddd(1), dddd(2), dddd(3), ptd1(0), ptd1(1), 50)
    
    
    intersd = ent.IntersectWith(crossline, acExtendNone)
    
    If UBound(intersd) >= 5 Then
    
    
    
        retd = getNearestTwo(intersd, pt1.x, pt1.y)
    
    
    Else
        ThisDrawing.Utility.prompt "오류가 발생했습니다"
    
    End If
    
    crossline.Delete    '확장 라인 삭제
    
    selectCrossPoints = retd

End Function

Attribute VB_Name = "ClsUndergroundParkingLot"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private isTest As Boolean

'"RD_SISUL_A_주요터널입구_170404|RD_SISUL_A_주요터널마킹_170405|RD_SISUL_L_주요터널히든선_170407"
Private lyrname_entrance As String
Private lyrname_marking As String
Private lyrname_hiddenline As String
 
Private ss As New clsSelSets
Private widthd As Double

Private ent As AcadEntity
    
    
Private pl1 As AcadEntity
Private pl2 As AcadEntity
    
Private ptd1() As Double
Private ptd2() As Double
Private ptd3() As Double
Private ptd4() As Double


Private line1dd() As Double
Private line2dd() As Double


Private ptd5() As Double
Private ptd7() As Double

Private ptd10() As Double
Private ptd12() As Double

Private ptd13() As Double
Private ptd14() As Double


Private pt1 As New clsPoint
Private pt2 As New clsPoint
Private pt3 As New clsPoint
Private pt4 As New clsPoint
    
Private pt5 As New clsPoint
Private pt7 As New clsPoint

Private pt10 As New clsPoint
Private pt12 As New clsPoint
    
Private pt13 As New clsPoint
Private pt14 As New clsPoint
    

Private rad As Double
Private dist1 As Double
Private dist2 As Double
 
Private tun1 As AcadEntity
Private tun2 As AcadEntity



Function setLayers(layers() As String)

    lyrname_entrance = layers(0)
    lyrname_marking = layers(1)
    lyrname_hiddenline = layers(2)
    
    'If lyrname_entrance Like "*주요*" Then
    '    dist1 = 3
    '    dist2 = 6.5
    '    rad = PI / 8
    'Else
    '    dist1 = 0.8
    '    dist2 = 1.72
    '    rad = PI / 10
    'End If
    
    
End Function

Function setdistance(d1 As Double, d2 As Double)

    dist1 = d1
    dist2 = d2

End Function

Function loadEx2()

    Dim layers() As String
    Dim lyrs(2) As String
    Dim selec As New ClsSelEntity

    Dim pr As New clsPolygonReader
    Dim plr As New ClsPolylineReader
    
    Dim pttd(2) As Double
    Dim ptt As New clsPoint
    
    Dim tmpptd() As Double

    On Error GoTo EndOfFunction
    Debug.Print "==================START ================="
    
    isTest = False
    
    'dist1 = 3.5
    'dist2 = 7.5
    'dist1 = 1.04
    'dist2 = 2.22
    
    
    Set ent = ss.selectPolyline
    If ent.Closed = False Then
        ThisDrawing.Utility.prompt "Polyline을 잘못 선택했습니다."
        GoTo EndOfFunction
    End If
        
    
    ThisDrawing.SetVariable "osmode", 544
    
    If isTest = False Then
        
        
        ptd1 = ThisDrawing.Utility.getPoint(, "Enter a point1: ")
        'ptd2 = ThisDrawing.Utility.getPoint(, "Enter a point2: ")
        'ptd3 = ThisDrawing.Utility.getPoint(, "Enter a point3: ")
        'ptd4 = ThisDrawing.Utility.getPoint(, "Enter a point4: ")
        
        'ptd1(0) = 222.808064798255
        'ptd1(1) = 613.404363855576
        'ptd3(0) = 322.417996325084
        'ptd3(1) = 600.936846717623
        
        Debug.Print "ptd1(0) = " & ptd1(0)
        Debug.Print "ptd1(1) = " & ptd1(1)
        
        tmpptd = selectCrossPoints(ent, ptd1)
        ptd1(0) = tmpptd(0)
        ptd1(1) = tmpptd(1)
        
        ReDim ptd2(2) As Double
        ptd2(0) = tmpptd(2)
        ptd2(1) = tmpptd(3)
        
        
        tmpptd = ThisDrawing.Utility.getPoint(, "Enter a point2: ")
        ReDim ptd4(2) As Double
        ptd4(0) = tmpptd(0)
        ptd4(1) = tmpptd(1)
        
        tmpptd = ThisDrawing.Utility.getPoint(, "Enter a point3: ")
        ReDim ptd3(2) As Double
        ptd3(0) = tmpptd(0)
        ptd3(1) = tmpptd(1)
        
        
        'addDonutA ptd1(0), ptd1(1)
        'addDonutA ptd2(0), ptd2(1)
        'addDonutA ptd3(0), ptd3(1)
        'addDonutA ptd4(0), ptd4(1)
        
        
    Else
        ReDim ptd1(1) As Double
        ReDim ptd2(1) As Double
        ReDim ptd3(1) As Double
        ReDim ptd4(1) As Double
         
ptd1(0) = 1106581.090286
ptd1(1) = 1688864.14762994
ptd2(0) = 1106581.65407904
ptd2(1) = 1688857.17037135
ptd3(0) = 1106590.27066761
ptd3(1) = 1688857.86662943
ptd4(0) = 1106589.73937065
ptd4(1) = 1688864.84587558
    
    End If
    
    
    Debug.Print "ptd1(0) = " & ptd1(0)
    Debug.Print "ptd1(1) = " & ptd1(1)
    Debug.Print "ptd2(0) = " & ptd2(0)
    Debug.Print "ptd2(1) = " & ptd2(1)
    Debug.Print "ptd3(0) = " & ptd3(0)
    Debug.Print "ptd3(1) = " & ptd3(1)
    Debug.Print "ptd4(0) = " & ptd4(0)
    Debug.Print "ptd4(1) = " & ptd4(1)



    addVertex ent, ptd1(0), ptd1(1)
    addVertex ent, ptd2(0), ptd2(1)
    addVertex ent, ptd3(0), ptd3(1)
    addVertex ent, ptd4(0), ptd4(1)


    pt1.initPt ptd1
    pt2.initPt ptd2
    pt3.initPt ptd3
    pt4.initPt ptd4
    
    
    widthd = getDistance(pt1.x, pt1.y, pt2.x, pt2.y)
    
    layers = getDefaultTunnelLayers
    
    
    
    'If widthd < 10.5 Then

    lyrs(0) = layers(0)
    lyrs(1) = layers(1)
    lyrs(2) = layers(2)
    
    setLayers lyrs
    
    Debug.Print "widthd: " & widthd
            
    'If widthd > 10 Then
    '    dist1 = 3
    '    dist2 = 6.5
    '    rad = PI / 8
    'Else
        dist1 = 0.8
        dist2 = 1.72
        rad = PI / 10
    'End If
    
    
    '위치 변경
    
    pttd(0) = ptd4(0)
    pttd(1) = ptd4(1)
    
    ptd4(0) = ptd1(0)
    ptd4(1) = ptd1(1)
    ptd1(0) = ptd2(0)
    ptd1(1) = ptd2(1)
    ptd2(0) = ptd3(0)
    ptd2(1) = ptd3(1)
    ptd3(0) = pttd(0)
    ptd3(1) = pttd(1)
    
    
    ptt.x = pt4.x
    ptt.y = pt4.y
    pt4.x = pt1.x
    pt4.y = pt1.y
    pt1.x = pt2.x
    pt1.y = pt2.y
    pt2.x = pt3.x
    pt2.y = pt3.y
    pt3.x = ptt.x
    pt3.y = ptt.y
    

    addDonut ptd1(0), ptd1(1)
    addDonut ptd2(0), ptd2(1)
    addDonut ptd3(0), ptd3(1)
    addDonut ptd4(0), ptd4(1)

    pr.init ent
    pr.setIndexByPoint pt1
    pr.setEIndexByPoint pt2
    
    line1dd = pr.getShortLine2
    
    pr.setIndexByPoint pt3
    pr.setEIndexByPoint pt4
    
    line2dd = pr.getShortLine2
    
    
    Set pl1 = ThisDrawing.ModelSpace.AddLightWeightPolyline(line1dd)
    pl1.color = acRed
    Set pl2 = ThisDrawing.ModelSpace.AddLightWeightPolyline(line2dd)
    

    plr.init pl1
    ptd5 = plr.getLineFromStart(dist1)
    
    addVertex ent, ptd5(0), ptd5(1)
    
    pt5.initPt ptd5
    
    addDonut ptd5(0), ptd5(1)
    
    ptd7 = plr.getLineWingPoint(pt1, pt5, dist2, -rad)
    
    pt7.initPt ptd7
    
    addDonut ptd7(0), ptd7(1)
    
    plr.init pl2
    ptd10 = plr.getLineFromEnd(dist1)
    
    addVertex ent, ptd10(0), ptd10(1)
    
    addDonut ptd10(0), ptd10(1)
     
    pt10.initPt ptd10
    
    ptd12 = plr.getLineWingPoint(pt4, pt10, dist2, rad)

    pt12.initPt ptd12
    
    addDonut ptd12(0), ptd12(1)
    setTunIn
    
    setCrossPoint
    
    setTunnel
    
 
    
   
    'setTunOut
    
    pl1.Delete
    pl2.Delete
EndOfFunction:
    
   
    

    Debug.Print "DONE"
    
    
    
End Function


Private Function setCrossPoint()

    Dim line1 As AcadLine
    Dim line2 As AcadLine
    Dim sp(0 To 2) As Double
    Dim ep(0 To 2) As Double
    Dim inters As Variant


    sp(0) = ptd7(0)
    sp(1) = ptd7(1)
    ep(0) = ptd12(0)
    ep(1) = ptd12(1)

    Set line1 = ThisDrawing.ModelSpace.addLine(sp, ep)
    line1.color = acRed
    
    inters = pl1.IntersectWith(line1, acExtendNone)
    
    ptd13 = addVertexH(pl1, inters(0), inters(1))
    pt13.initPt ptd13
    
    inters = pl2.IntersectWith(line1, acExtendNone)
    ptd14 = addVertexH(pl2, inters(0), inters(1))
    pt14.initPt ptd14

    
    addDonut ptd13(0), ptd13(1)
    addDonut ptd14(0), ptd14(1)

    
    Debug.Print ""
    line1.Delete
    
    

End Function



Public Function setTunnel()
   Dim tmp(13) As Double
   Dim pr1 As New clsPolygonReader
   Dim pr2 As New clsPolygonReader
    Dim ddd1() As Double
    Dim ddd2() As Double
    Dim merge As New ClsMerger
    Dim size As Integer
    Dim ll1(3) As Double
    Dim ll2(3) As Double
    Dim ent As AcadEntity
    Dim hline1 As AcadEntity
    Dim hline2 As AcadEntity
   
   Dim tmp1 As AcadEntity
   Dim tmp2 As AcadEntity
   
   pr1.init pl1
   pr1.setIndexByPoint pt13
   pr1.setEIndexByPoint pt2
   
   'addDonutA pt13.x, pt13.y
   'addDonutA pt15.x, pt15.y
   
   pr1.setIndex 0
   
   ddd1 = pr1.getShortLine2Half()
   
   
   pr2.init pl2
   pr2.setIndexByPoint pt3
   pr2.setEIndexByPoint pt14
   
   ddd2 = pr2.getShortLine2Half()
  
  
    pl1.color = acRed
    pl2.color = acRed
  
    'Set tmp1 = ThisDrawing.ModelSpace.AddLightWeightPolyline(ddd1)
    'tmp1.color = acGreen
    'Set tmp2 = ThisDrawing.ModelSpace.AddLightWeightPolyline(ddd2)
    'tmp2.color = acGreen
  
   ll1(0) = ptd13(0)
   ll1(1) = ptd13(1)
   ll1(2) = ptd14(0)
   ll1(3) = ptd14(1)
   
   ll2(0) = ptd2(0)
   ll2(1) = ptd2(1)
   ll2(2) = ptd3(0)
   ll2(3) = ptd3(1)
   
   
   
   size = UBound(ddd1) + UBound(ddd2) + UBound(ll1) + UBound(ll2) + 3
   
   merge.setSize size
   merge.add ddd1
   merge.add ll2
   merge.add ddd2
   merge.add ll1
   
   Set ent = ThisDrawing.ModelSpace.AddLightWeightPolyline(merge.getMerged())
   ent.Closed = True
   ent.layer = getAddLayerName(lyrname_marking)
   
   
   Set hline1 = ThisDrawing.ModelSpace.AddLightWeightPolyline(ddd1)
   hline1.layer = getAddLayerName(lyrname_hiddenline)
   Set hline2 = ThisDrawing.ModelSpace.AddLightWeightPolyline(ddd2)
   hline2.layer = getAddLayerName(lyrname_hiddenline)
   
   Debug.Print ""
    
    
    
End Function

Public Function setTunIn()
    Dim tmp() As Double
    Dim pr As New clsPolygonReader
    Dim ddd1() As Double
    Dim ddd2() As Double
    Dim idx As Integer
    
    
    pr.init ent
    pr.setIndexByPoint pt4
    pr.setEIndexByPoint pt10
    
    ddd1 = pr.getShortLine2
    
    pr.setIndexByPoint pt5
    pr.setEIndexByPoint pt1
    
    ddd2 = pr.getShortLine2
    
    
    ReDim tmp(6 + UBound(ddd1) + UBound(ddd2) + 1)
    
    tmp(0) = pt1.x
    tmp(1) = pt1.y
    tmp(2) = pt7.x
    tmp(3) = pt7.y
    tmp(4) = pt12.x
    tmp(5) = pt12.y
    
    idx = 6
   
    
    For i = 0 To UBound(ddd1) Step 2
        'addDonutA ddd1(i), ddd1(i + 1)
        tmp(idx) = ddd1(i)
        tmp(idx + 1) = ddd1(i + 1)
        idx = idx + 2
    Next i
    
    'tmp(6) = pt4.x
    'tmp(7) = pt4.y
    'tmp(8) = pt10.x
    'tmp(9) = pt10.y
    
    For i = 0 To UBound(ddd2) Step 2
        'addDonutA ddd2(i), ddd2(i + 1)
        tmp(idx) = ddd2(i)
        tmp(idx + 1) = ddd2(i + 1)
        idx = idx + 2
    Next i
    
    'tmp(10) = pt5.x
    'tmp(11) = pt5.y
    'tmp(12) = pt1.x
    'tmp(13) = pt1.y
    
    Set tun1 = ThisDrawing.ModelSpace.AddLightWeightPolyline(tmp)
    tun1.Closed = True
    tun1.layer = getAddLayerName(lyrname_entrance)
    
    
End Function
 

Public Function setTunOut()
    Dim tmp(13) As Double
    
    tmp(0) = pt2.x
    tmp(1) = pt2.y
    tmp(2) = pt8.x
    tmp(3) = pt8.y
    tmp(4) = pt11.x
    tmp(5) = pt11.y
    tmp(6) = pt3.x
    tmp(7) = pt3.y
    tmp(8) = pt9.x
    tmp(9) = pt9.y
    tmp(10) = pt6.x
    tmp(11) = pt6.y
    tmp(12) = pt2.x
    tmp(13) = pt2.y
    
    Set tun2 = ThisDrawing.ModelSpace.AddLightWeightPolyline(tmp)
    tun2.Closed = True
    tun2.layer = getAddLayerName(lyrname_entrance)
    
End Function

Public Function selectCrossPoints(ent As AcadEntity, ptd1() As Double) As Double()

    Dim selec As New clsSelSets
    Dim pt1 As New clsPoint
    Dim ptprev As New clsPoint
    Dim ptnext As New clsPoint
    Dim pr As New clsPolygonReader
    Dim alpha As Double
    Dim ddd(3) As Double
    Dim dddd() As Double
    Dim retd() As Double
    Dim crossline As AcadEntity
    Dim intersd() As Double
    
    ptd1 = addVertex(ent, ptd1(0), ptd1(1))
    
    pt1.initPt ptd1
    
    pr.init ent
    pr.setIndexByPoint pt1
    pr.setIndex pr.getSIndex
    
    addDonut pt1.x, pt1.y
    
    Set ptprev = pr.prevPoint
    Set ptnext = pr.nextPoint
    Set ptnext = pr.nextPoint
    
    ddd(0) = ptprev.x
    ddd(1) = ptprev.y
    ddd(2) = ptnext.x
    ddd(3) = ptnext.y
    
    Set crossline = ThisDrawing.ModelSpace.AddLightWeightPolyline(ddd)
    crossline.color = acRed
    
    
    ReDim ptd1(2) As Double
    ptd1(0) = pt1.x
    ptd1(1) = pt1.y
    crossline.Rotate ptd1, PI / 2
    
    dddd = crossline.Coordinates
    crossline.Delete    '라인 삭제
    
    Set crossline = extendLineBoth(dddd(0), dddd(1), dddd(2), dddd(3), ptd1(0), ptd1(1), 50)
    
    
    intersd = ent.IntersectWith(crossline, acExtendNone)
    
    If UBound(intersd) >= 5 Then
    
    
    
        retd = getNearestTwo(intersd, pt1.x, pt1.y)
    
    
    Else
        ThisDrawing.Utility.prompt "오류가 발생했습니다"
    
    End If
    
    crossline.Delete    '확장 라인 삭제
    
    selectCrossPoints = retd

End Function

Attribute VB_Name = "ClsUnionPolyline"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private plroad() As AcadEntity
Private size As Integer

Private layername As String



Function load()
    
    Dim ent1 As AcadEntity
    Dim ent2 As AcadEntity
    
    Dim reg1 As AcadRegion
    Dim reg2 As AcadRegion
    
    Dim ttt As Variant
    
    Dim regs() As AcadRegion
    
    Dim ents() As AcadEntity
    Dim entsuni() As AcadEntity
    
    Dim idx As Integer
    
    
    Dim cnt As Integer
    
    Dim bcheck As Boolean
    Dim resent As AcadEntity
    
    plroad = selectPolylineObs
    
    size = UBound(plroad)
    layername = ""
    bcheck = True
    
    For i = 0 To size
        Set ent1 = plroad(i)
        
        If layername = "" Then
            layername = ent1.layer
        Else
        
            If layername <> ent1.layer Then
                bcheck = False
            End If
        
        End If
        
        If ent1.Closed = True Then
            cnt = cnt + 1
        End If
    Next i
    
    If bcheck = True Then   '레이어 이름이 동일함
    
    
        ReDim regs(cnt - 1) As AcadRegion
        
        idx = 0
        
        For i = 0 To size
            Set ent1 = plroad(i)
            ReDim ents(0) As AcadEntity
            Set ents(0) = ent1
            
            If ent1.Closed = True Then
                ttt = ThisDrawing.ModelSpace.AddRegion(ents)
                Set regs(idx) = ttt(0)
                idx = idx + 1
            End If
            
        Next i
        
        Set reg1 = regs(0)
        
        For i = 1 To cnt - 1
            regs(0).Boolean acUnion, regs(i)
             
        Next i
        
        Set resent = expoldeRegion(regs(0))(0)
        
        
        resent.layer = getAddLayerName(layername)
        
        change_layername
    Else
    
        MsgBox "레이어 이름이 동일하지 않습니다."
        'ThisDrawing.Utility.prompt
    
    End If
 
End Function




Function loadEx()   '보완
    
    Dim ent1 As AcadEntity
    Dim ent2 As AcadEntity
    
    Dim reg1 As AcadRegion
    Dim reg2 As AcadRegion
    
    Dim unireg As AcadRegion
    
    Dim ttt As Variant
    
    Dim regs() As AcadRegion
    
    Dim ents() As AcadEntity
    
    Dim idx As Integer
    
    Dim cnt As Integer
    
    Dim bcheck As Boolean
    Dim resent As AcadEntity
    
    Dim temp1 As AcadEntity
    Dim temp2 As AcadEntity
    
    Dim col As New Collection
    
    Dim areainter As Double
    
    plroad = selectPolylineObs
    
    
    
    
    size = UBound(plroad)
    layername = ""
    bcheck = True
    
    For i = 0 To size
        Set ent1 = plroad(i)
        
        If layername = "" Then
            layername = ent1.layer
        Else
        
            If layername <> ent1.layer Then
                bcheck = False
            End If
        
        End If
        
        If ent1.Closed = True Then
            cnt = cnt + 1
        End If
    Next i
    
    If bcheck = True Then   '레이어 이름이 동일함
    
    
        ReDim regs(cnt - 1) As AcadRegion
        
        idx = 0
        
        For i = 0 To size
            Set ent1 = plroad(i)
            ReDim ents(0) As AcadEntity
            Set ents(0) = ent1
            
            If ent1.Closed = True Then
                ttt = ThisDrawing.ModelSpace.AddRegion(ents)
                Set regs(idx) = ttt(0)
                idx = idx + 1
            End If
            
        Next i
        
        Set reg1 = regs(0)
        
        For i = 1 To cnt - 1
            regs(0).Boolean acUnion, regs(i)
             
        Next i
        
        'Set resent = expoldeRegion(regs(0))
        '
        '
        'resent.layer = getAddLayerName(layername)
        
        Set unireg = regs(0)
        
        
        ReDim regs(cnt - 1) As AcadRegion
        
        idx = 0
        
        For i = 0 To size
            Set ent1 = plroad(i)
            ReDim ents(0) As AcadEntity
            Set ents(0) = ent1
            
            If ent1.Closed = True Then
                ttt = ThisDrawing.ModelSpace.AddRegion(ents)
                Set regs(idx) = ttt(0)
                idx = idx + 1
            End If
            
        Next i
         
        
        For i = 0 To cnt - 1
            For j = i + 1 To cnt - 1
                Set temp1 = regs(i).Copy
                temp1.color = acBlue
                temp1.Update
                Set temp2 = regs(j).Copy
                temp2.color = acBlue
                temp2.Update
                
                
                temp1.Boolean acIntersection, temp2
                Set temp1 = temp1
                temp1.color = acRed
                temp1.Update
                
                
                If areainter < temp1.area Then
                    areainter = temp1.area
                
                End If
                
                Debug.Print "AREA: " & areainter
                
                col.add temp1
                
            Next j
            
            regs(i).Delete
        Next i
        
        For i = 1 To col.count
        
            Set temp1 = col(i).Copy
            temp1.color = acBlue
        
            unireg.Boolean acSubtraction, temp1
        
        
        Next i
        
        entsuni = expoldeRegion(unireg)
        
        Set reg1 = Nothing
        Set reg2 = Nothing
        
        For i = 0 To UBound(entsuni)
            ReDim ents(0) As AcadEntity
            Set ents(0) = entsuni(i)
            
            If entsuni(i).Closed = True And entsuni(i).area > areainter * 3 Then
                Set reg2 = ThisDrawing.ModelSpace.AddRegion(ents)(0)
                
                If reg1 Is Nothing Then
                
                    Set reg1 = reg2
                    
                Else
                    reg1.Boolean acUnion, reg2
                End If
                
                
                
                
            End If
            
            entsuni(i).Delete
            
        Next i
        
        
        For i = 1 To col.count
            Set temp1 = col(i)
        
            reg1.Boolean acUnion, temp1
        Next i
        
        reg1.color = acCyan
        
        Set resent = expoldeRegion(reg1)(0)
        resent.layer = getAddLayerName(layername)
         
        
        change_layername
    Else
    
        MsgBox "레이어 이름이 동일하지 않습니다."
        'ThisDrawing.Utility.prompt
    
    End If
 
End Function


Function change_layername()

    Dim ent As AcadEntity
    
        
    For i = 0 To size
        Set ent = plroad(i)
        
        If ent.Closed = True Then
        
            If layername = "0" Then
                ent.Delete
            Else
        
                ent.layer = getDelLayerName(layername)
            End If
        End If
    Next i


End Function

Attribute VB_Name = "ClsValidator"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private lyrname As String
Private tblname As String
Private dict As Dictionary
Private dictdup As Dictionary


Private entpt As AcadPoint
Private entpl As AcadLWPolyline
Private entl As AcadLine

Private circleobj As AcadCircle
Private ptd2(0 To 2) As Double



Function init(lname As String, tname As String)

    lyrname = lname
    tblname = tname
    
    Set dict = New Dictionary
    Set dictdup = New Dictionary
    
End Function


Function check_mid()
    Dim polylines As AcadSelectionSet
    Dim FilterType(0) As Integer
    Dim FilterData(0) As Variant
    Dim pl As AcadEntity
    Dim cols As New Collection
    Dim odinfo As New ClsODInfo
    Dim isvalid As Boolean
    Dim ptt As AcadPoint
    
    Dim obj As Variant
    Dim mid As Variant
    Dim cnt As Integer
    
    Dim coldu As New Collection
    
    On Error Resume Next
    
    Set polylines = ThisDrawing.SelectionSets.add("polylinesSS")
    
    If Err.Number <> 0 Then
        ThisDrawing.SelectionSets.Item("polylinesSS").Delete
        Set polylines = ThisDrawing.SelectionSets.add("polylinesSS")
    End If
    
    FilterType(0) = 8
    FilterData(0) = lyrname
    
    polylines.Select acSelectionSetAll, , , FilterType, FilterData
    
    Debug.Print "object size: "; polylines.count
    
    For Each entity In polylines
        Set pl = entity
        
        odinfo.init pl, tblname
        isvalid = odinfo.setTableInstance
        
        If isvalid = True Then
        
            obj = odinfo.getInfoByName("MID")
            
            If obj = Empty Then
                Exit For
                
            End If
            
            cols.add obj
        Else
            'Debug.Print tblname & ": Break"
            Exit For
        
        End If
        
    Next
    
    If cols Is Nothing Or cols.count = 0 Then
        'Debug.Print "size: EMPTY"
    Else
    
        
     
        For Each entity In polylines
        
            cnt = 0
        
            Set pl = entity
    
            odinfo.init pl, tblname
            isvalid = odinfo.setTableInstance
           
            mid = odinfo.getInfoByName("MID")
            
            For i = 1 To cols.count
            
                obj = cols.Item(i)
                'Debug.Print mid & ", " & obj
                If obj = mid Then
                
                    cnt = cnt + 1
                End If
                    
            Next i
            

            
            If cnt > 1 Then
                Debug.Print "mid: " & mid & "> size: " & cnt
                coldu.add mid
            End If
        Next
    
   
        
    End If
    
    If coldu Is Nothing Or coldu.count = 0 Then
        'Debug.Print "size: EMPTY"
    Else
    
        For Each entity In polylines
            Set ptt = entity
            
    
            odinfo.init ptt, tblname
            isvalid = odinfo.setTableInstance
           
            mid = odinfo.getInfoByName("MID")
            
             For i = 1 To coldu.count
            
                obj = coldu.Item(i)
                Debug.Print mid & ", " & obj
                If obj = mid Then
                
                    
                    addDonutA ptt.Coordinates(0), ptt.Coordinates(1)
                    
                End If
                    
            Next i
            
        Next
        
    
    End If
    
    
End Function

Function check_mid2() As Integer
    Dim polylines As AcadSelectionSet
    Dim FilterType(0) As Integer
    Dim FilterData(0) As Variant
    Dim pl As AcadEntity
     
    Dim odinfo As New ClsODInfo
    Dim isvalid As Boolean
    
    
    Dim obj As Variant
    Dim mid As Variant
    Dim mid1 As Variant
    Dim mid2 As Variant
    Dim cnt As Integer
    
    Dim colpts As New Collection
    Dim pts() As Double
    
    
    Dim obj1 As AcadObject
    
    Dim dx As Double
    Dim dy As Double
    
    
    On Error Resume Next
    
    Set polylines = ThisDrawing.SelectionSets.add("polylinesSS")
    
    If Err.Number <> 0 Then
        ThisDrawing.SelectionSets.Item("polylinesSS").Delete
        Set polylines = ThisDrawing.SelectionSets.add("polylinesSS")
    End If
    
    FilterType(0) = 8
    FilterData(0) = lyrname
    
    polylines.Select acSelectionSetAll, , , FilterType, FilterData
    
    Debug.Print "object size: "; polylines.count
    
    For Each entity In polylines
        Set pl = entity
        
        odinfo.init pl, tblname
        isvalid = odinfo.setTableInstance
        
        If isvalid = True Then
        
            obj = odinfo.getInfoByName("mid")
            
            If obj = Empty Then
                Exit For
                
            End If
            
            Dim data As New ClsObjectData
            data.setData pl.ObjectID, obj
            dict.add key:="" & pl.ObjectID, Item:=obj
        Else
            'Debug.Print tblname & ": Break"
            Exit For
        
        End If
        
    Next
    
    For Each key1 In dict.Keys
    
        cnt = 0
        mid1 = dict.Item(key1)
        
        For Each key2 In dict.Keys
        
            If StrComp(key1, key2) <> 0 Then
        
                mid2 = dict.Item(key2)
                
                If mid1 = mid2 Then
                    cnt = cnt + 1
                End If
            End If
        
        Next
        
        If cnt > 0 Then
            dictdup.add key:="" & mid1, Item:=mid1
            
        End If
        
        'Debug.Print "MID: " & mid1 & ">" & cnt
    
    Next
     
    
    For Each mid1 In dictdup.Keys
        
        mid1 = dictdup.Item(mid1)
        For Each key2 In dict.Keys
        
            mid2 = dict.Item(key2)
        
            'Debug.Print "MID1: " & mid1 & ", MID2: " & mid2
        
            Set colpts = New Collection
        
            If mid1 = mid2 Then
                
                
                Set obj1 = ThisDrawing.ObjectIdToObject(key2) 'objectid
                       
                Set circleobj = Nothing
                       
                If TypeOf obj1 Is AcadPoint Then
                
                    Set entpt = obj1
                    ptd2(0) = entpt.Coordinates(0)
                    ptd2(1) = entpt.Coordinates(1)
                              
                    
                    colpts.add dx
                    colpts.add dy
                    'colpts.add 0
                    
                    'Debug.Print "dx: " & dx & ", dy: " & dy
                    Set circleobj = ThisDrawing.ModelSpace.AddCircle(ptd2, 3)
                    'circleobj.layer = "MIDüũ"
                    'circleobj.color = acMagenta
                    'obj1.color = acMagenta
                    
                ElseIf TypeOf obj1 Is AcadLWPolyline Then
                    Set entpl = obj1
                    ptd2(0) = entpl.Coordinates(0)
                    ptd2(1) = entpl.Coordinates(1)
                              
                    Set circleobj = ThisDrawing.ModelSpace.AddCircle(ptd2, 3)
                     
                ElseIf TypeOf obj1 Is AcadLine Then
                
                    Set entl = obj1
                    ptd2(0) = entl.startPoint(0)
                    ptd2(1) = entl.startPoint(1)
                              
                    Set circleobj = ThisDrawing.ModelSpace.AddCircle(ptd2, 3)
                    'addDonutA ptd2(0), ptd2(1)
                
                Else
                
                    Debug.Print "!!!!!!!!!!!!!!!!! check !!!!!!!!!!!!!!!!!!"
                
                End If
                       
                If (circleobj Is Nothing) = False Then
                    'circleobj.layer = "MIDüũ"
                    circleobj.color = acMagenta
                    obj1.color = acMagenta
                    circleobj.Update
                    
                    
                    
                End If
                       
            End If
            
            
            'pts = toArray(colpts)
            'ThisDrawing.ModelSpace.AddLightWeightPolyline pts
            
            
            
        Next
                
        
    Next
    
    
    check_mid2 = dictdup.count
    
    
End Function




Function toArray(col As Collection) As Double()
  Dim arr() As Double
  ReDim arr(0 To col.count - 1) As Double
  For i = 1 To col.count
      arr(i - 1) = col(i)
  Next
  toArray = arr
End Function

Attribute VB_Name = "ClsValidatorEx"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private prloader As New ClsPropLoader
Private dictlyr As New Dictionary


Private dictobj As New Dictionary


Private dictdup As Dictionary

Private circleobj As AcadCircle
Private ptd2(0 To 2) As Double


Private duptotal As Long



Public Function load()
    
    Dim lyr As AcadLayer
    Dim cnt As Integer
    Dim lyrkey As String
    Dim lyrname As String
    Dim lyrname2 As String
    
    Dim dupcnt As Integer
    Dim duptotal As Integer
    Dim tblpath As String
    
    Dim bret As Boolean
    
    
    Set dictdup = New Dictionary
    
    duptotal = 0
    cnt = ThisDrawing.layers.count
    
    
    tblpath = getMIDTablePropFile
    
    If tblpath = "" Then
    
        Exit Function
    End If
    
    
    bret = prloader.load_data(tblpath)
    
    If bret = False Then
        Exit Function
    End If
    
    For Each key In prloader.getKeys
        lyrkey = key
        
        For idx = 0 To cnt - 1
            Set lyr = ThisDrawing.layers.Item(idx)
            lyrname = lyr.name
    
            If startsWith(lyrname, "!!변경_") = True Or startsWith(lyrname, "!!삭제_") = True Then
        
                lyrname2 = Replace(lyrname, "!!변경_", "")
                'lyrname2 = Replace(lyrname2, "!!추가_", "")
                lyrname2 = Replace(lyrname2, "!!삭제_", "")
            
            
                lyrname2 = prloader.getValue(lyrname2)
            
                If startsWith(lyrname2, lyrkey) = True Then
                    If dictlyr.exists(lyrkey) = False Then
                        dictlyr.add key:="" & lyrkey, Item:=lyrname
                    Else
                        values = dictlyr.Item(lyrkey)
                        dictlyr.remove (lyrkey)
                        
                        values = values & "," & lyrname
                        
                        dictlyr.add key:="" & lyrkey, Item:="" & values
                    
                    End If
                End If
            
                 
                'dupcnt = vd.check_mid2
                'duptotal = duptotal + dupcnt
                'ThisDrawing.Utility.prompt lyrname + " 작업완료. 중복:" & dupcnt & vbCrLf
            End If
        Next idx
        
    Next
    
  
End Function


Public Function loaddata()

    Dim vrr() As String
    Dim cnt As Integer
    Dim tblname As String
    
    For Each key In dictlyr.Keys
    
        Debug.Print key & " > " & dictlyr.Item(key)
        
        tblname = gettablename(dictlyr.Item(key))
        
        If tblname <> "" Then
            
            vrr() = Split(dictlyr.Item(key), ",")
            
            cnt = UBound(vrr)
            
            For idx = 0 To cnt
            
                loadmid vrr(idx), tblname
            
            Next idx
        End If
        
        check_dup
        
        show_dup
        
        dictobj.RemoveAll
        dictdup.RemoveAll
        
    Next
    
    
    ThisDrawing.Utility.prompt "레이어 전체. 중복:" & duptotal & vbCrLf

End Function

Private Function check_dup()

    Dim key1 As Variant
    Dim key2 As Variant

    Dim mid1 As Variant
    Dim mid2 As Variant
    
    Dim ooo As Variant
    Dim cnt As Integer

    For Each key1 In dictobj.Keys
    
        cnt = 0
        mid1 = dictobj.Item(key1)
        
        For Each key2 In dictobj.Keys
        
            If StrComp(key1, key2) <> 0 Then
        
                mid2 = dictobj.Item(key2)
                
                If mid1 = mid2 Then
                    cnt = cnt + 1
                End If
            End If
        
        Next
        
        If cnt > 0 Then
            If dictdup.exists("" & mid1) = False Then
                dictdup.add key:="" & mid1, Item:=mid1
            End If
        End If
        
        'Debug.Print "MID: " & mid1 & ">" & cnt
    
    Next
    
    duptotal = duptotal + dictdup.count
    
    
End Function

Private Function show_dup()

    Dim mid1 As Variant
    Dim mid2 As Variant
    
    Dim obj1 As Variant
    Dim colpts As New Collection
    Dim entpl As AcadLWPolyline

    For Each mid1 In dictdup.Keys
        
        mid1 = dictdup.Item(mid1)
        For Each key2 In dictobj.Keys
        
            mid2 = dictobj.Item(key2)
        
            Debug.Print "MID1: " & mid1 & ", MID2: " & mid2
        
            Set colpts = New Collection
        
            If mid1 = mid2 Then
                
                
                Set obj1 = ThisDrawing.ObjectIdToObject(key2) 'objectid
                       
                Set circleobj = Nothing
                       
                If TypeOf obj1 Is AcadPoint Then
                
                    Set entpt = obj1
                    ptd2(0) = entpt.Coordinates(0)
                    ptd2(1) = entpt.Coordinates(1)
                              
                    
                    colpts.add dx
                    colpts.add dy
                    'colpts.add 0
                    
                    'Debug.Print "dx: " & dx & ", dy: " & dy
                    Set circleobj = ThisDrawing.ModelSpace.AddCircle(ptd2, 3)
                    'circleobj.layer = "MID체크"
                    'circleobj.color = acMagenta
                    'obj1.color = acMagenta
                    
                ElseIf TypeOf obj1 Is AcadLWPolyline Then
                    Set entpl = obj1
                    
                    ptd2(0) = entpl.Coordinates(0)
                    ptd2(1) = entpl.Coordinates(1)
                              
                    Set circleobj = ThisDrawing.ModelSpace.AddCircle(ptd2, 3)
                     
                ElseIf TypeOf obj1 Is AcadLine Then
                
                    Set entl = obj1
                    ptd2(0) = entl.startPoint(0)
                    ptd2(1) = entl.startPoint(1)
                              
                    Set circleobj = ThisDrawing.ModelSpace.AddCircle(ptd2, 3)
                    'addDonutA ptd2(0), ptd2(1)
                
                Else
                
                    Debug.Print "!!!!!!!!!!!!!!!!! check !!!!!!!!!!!!!!!!!!"
                
                End If
                       
                If (circleobj Is Nothing) = False Then
                    'circleobj.layer = "MID체크"
                    circleobj.color = acMagenta
                    obj1.color = acMagenta
                    circleobj.Update
                    
                    
                    
                End If
                       
            End If
            
            
            'pts = toArray(colpts)
            'ThisDrawing.ModelSpace.AddLightWeightPolyline pts
            
            
            
        Next
                
        
    Next
End Function

Private Function loadmid(lyrname As String, tblname As String)

    Dim polylines As AcadSelectionSet
    Dim FilterType(0) As Integer
    Dim FilterData(0) As Variant
    Dim pl As AcadEntity
    Dim odinfo As New ClsODInfo
    Dim isvalid As Boolean
    Dim obj As Variant

    On Error Resume Next
    Set polylines = ThisDrawing.SelectionSets.add("polylinesSS")
    
    If Err.Number <> 0 Then
        ThisDrawing.SelectionSets.Item("polylinesSS").Delete
        Set polylines = ThisDrawing.SelectionSets.add("polylinesSS")
    End If
    
    FilterType(0) = 8
    FilterData(0) = lyrname
    
    polylines.Select acSelectionSetAll, , , FilterType, FilterData
    
    Debug.Print "object size: "; polylines.count
    
    For Each entity In polylines
        Set pl = entity
        
        odinfo.init pl, tblname
        isvalid = odinfo.setTableInstance
        
        If isvalid = True Then
        
            obj = odinfo.getInfoByName("mid")
            
            If obj = Empty Then
                Exit For
                
            End If
            
            Dim data As New ClsObjectData
            data.setData pl.ObjectID, obj
            dictobj.add key:="" & pl.ObjectID, Item:=obj
        Else
            'Debug.Print tblname & ": Break"
            Exit For
        
        End If
        
    Next

End Function

Private Function gettablename(lyrname As String) As String

    Dim ent As AcadEntity
    
    Set ent = selectObjectFromLayer(lyrname)
    
    tblname = hasTablename(ent)

    ThisDrawing.Utility.prompt "테이블이름: " & tblname

    gettablename = tblname
    

End Function

Attribute VB_Name = "ClsWing"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private ptd1() As Double
Private ptd2() As Double

Private pt1 As New clsPoint
Private pt2 As New clsPoint


Private entbase As AcadEntity
Private lineorg As AcadLWPolyline
Private linenew As AcadLWPolyline
Private linetmp As AcadLWPolyline

Private pttmp As Variant

Private entref As AcadEntity
Private ptref As New clsPoint
Private ptrefd() As Double


Private lineref As AcadEntity
Private width As Double

 

Function load()
    Dim selec1 As New ClsSelEntity
    Dim selec2 As New ClsSelEntity
    Dim selec3 As New ClsSelEntity
    
    Dim ptt(2) As Double
    
    Dim ss As New clsSelSets
    
    
    Dim pr As New clsPolygonReader
    
    Dim ent As AcadEntity
    Dim b As Boolean
    

    Dim ptd3(2) As Double
    
    Dim ddd As Variant
    
    Dim ent2 As AcadLWPolyline
    Dim dir As String
    Dim rad As Double
    
    
    Dim line As AcadLine
    
    Dim merge As New ClsMerger
    
    Set ent = ss.selectPolyline
    Set entbase = ent.Copy
    
    
    Dim orgsplit() As Double
    Dim newsplit() As Double
    Dim addsplit(3) As Double
    
    Dim dist As Double
    
    
    width = getDefaultWingWidth
    
    rad = 0.02
    
    
    'selec1.selectPolyline ("#Get Polyline 1: ")
    
    'Set ent = selec1.getEntity
    
    ThisDrawing.SetVariable "osmode", 544
    ptd1 = ThisDrawing.Utility.getPoint(, "Enter a point1: ")
    ptd2 = ThisDrawing.Utility.getPoint(, "Enter a point2: ")
   
    pt1.x = ptd1(0)
    pt1.y = ptd1(1)
    pt2.x = ptd2(0)
    pt2.y = ptd2(1)
   
   
    selec1.selectPolyline ("#Get Polyline 1: ")
    Set entref = selec1.getEntity
    Set entref = entref.Copy
    ptrefd = selec1.getPointD
    
    
    ptrefd = addVertex2(entref, ptrefd(0), ptrefd(1))
    
    
    'addDonutA ptrefd(0), ptrefd(1)
    
    Set lineref = extendLine(ptrefd(0), ptrefd(1), ptd2(0), ptd2(1), 5)
    entref.Delete
   
    addVertex entbase, pt1.x, pt1.y
    addVertex entbase, pt2.x, pt2.y
    
    'addDonutA pt1.x, pt1.y
    'addDonutA pt2.x, pt2.y
    
    d = getDistance(pt1.x, pt1.y, pt2.x, pt2.y)
    
    
    rad = width / d
   
    
    pr.init entbase
    pr.setIndexByPoint pt1
    pr.setEIndexByPoint pt2
    
    ddd = pr.getShortLine2
    Set lineorg = ThisDrawing.ModelSpace.AddLightWeightPolyline(ddd)
    
    Set linenew = checkDirection(lineorg, rad, ptd1, ptrefd)
    
    
    'rad = getRadianValue(pt1.x, pt1.y, pt2.x, pt2.y, ptrefd(0), ptrefd(1), rad)
   
    
    'Debug.Print "rad: " & rad
    
    'Set linenew = lineorg.Copy
    
    'linenew.Rotate ptd1, rad
    
    
    orgsplit = lineorg.Coordinates
    newsplit = linenew.Coordinates
    
    lastExtend newsplit
    
    
    Set linetmp = ThisDrawing.ModelSpace.AddLightWeightPolyline(newsplit)
    pttmp = linetmp.IntersectWith(lineref, acExtendNone)
    linetmp.Delete
    'addDonutA pttmp(0), pttmp(1)
    
    size1 = UBound(orgsplit)
    size2 = UBound(newsplit)
    
    newsplit(size2 - 1) = pttmp(0)
    newsplit(size2) = pttmp(1)
    
    
    If newsplit(0) = ptd1(0) And newsplit(1) = ptd1(1) Then
    
        ptd3(0) = newsplit(size2 - 1)
        ptd3(1) = newsplit(size2)
    
    Else
        ptd3(0) = newsplit(0)
        ptd3(1) = newsplit(1)
    
    End If
    
    
    'Set line = ThisDrawing.ModelSpace.addLine(ptd2, ptd3)
    
    
    addsplit(0) = ptd3(0)
    addsplit(1) = ptd3(1)
    addsplit(2) = ptd2(0)
    addsplit(3) = ptd2(1)
    
    'line.color = acBlue
     
    'addDonutA ptd3(0), ptd3(1)
    'addDonutA ptd2(0), ptd2(1)
    
    size3 = 4
    
    merge.setSize size1 + size2 + size3 + 1
    
    
    merge.add orgsplit
    merge.add addsplit
    merge.add newsplit
    
    
    ddd = merge.getMerged
    
    ThisDrawing.ModelSpace.AddLightWeightPolyline ddd
    entbase.Delete
    lineorg.Delete
    linenew.Delete
    lineref.Delete
    
End Function


Function lastExtend(ddd() As Double)

    Dim x1 As Double
    Dim y1 As Double
    Dim x2 As Double
    Dim y2 As Double
    Dim dx As Double
    Dim dy As Double
    
    Dim size As Integer
    
    size = UBound(ddd)
    
    x1 = ddd(size - 3)
    y1 = ddd(size - 2)
    x2 = ddd(size - 1)
    y2 = ddd(size)
    
    dx = x2 - x1
    dy = y2 - y1
    
    x2 = x1 + dx * 3
    y2 = y1 + dy * 3
    
    ddd(size - 1) = x2
    ddd(size) = y2
    
    

End Function

Function checkDirection(ent As AcadEntity, rad As Double, ptd() As Double, ptr() As Double) As AcadEntity

    Dim entref1 As AcadEntity
    Dim entref2 As AcadEntity

    Dim ddd1() As Double
    Dim ddd2() As Double
    
    Dim pt1 As New clsPoint
    Dim pt2 As New clsPoint
    
    Dim d1 As Double
    Dim d2 As Double
    
    Dim size As Integer
    Dim ret As AcadEntity
    
    Set entref1 = ent.Copy
    entref1.Rotate ptd, rad
    
    Set entref2 = ent.Copy
    entref2.Rotate ptd, -rad
    
    
    ddd1 = entref1.Coordinates
    ddd2 = entref2.Coordinates
    
    size = UBound(ddd1)
    
    
    pt1.x = ddd1(size - 1)
    pt1.y = ddd1(size)
    
    pt2.x = ddd2(size - 1)
    pt2.y = ddd2(size)
    
    'addDonutA pt1.x, pt1.y
    'addDonutA pt2.x, pt2.y
    
    d1 = getDistance(pt1.x, pt1.y, ptr(0), ptr(1))
    d2 = getDistance(pt2.x, pt2.y, ptr(0), ptr(1))
    
    If d1 > d2 Then
        Set ret = entref1
        entref2.Delete
    Else
        Set ret = entref2
        entref1.Delete
    End If
    
    Set checkDirection = ret
    
   

End Function


Function getRadianValue(x1 As Double, y1 As Double, x2 As Double, y2 As Double, x3 As Double, y3 As Double, rad As Double) As Double
    
    Dim dist As Double
    Dim nx1 As Double
    Dim ny1 As Double
    Dim nx2 As Double
    Dim ny2 As Double
    
    Dim d1 As Double
    Dim d2 As Double
    
    Dim ret As Double
    
    dist = getDistance(x1, y1, x2, y2)
    nx1 = x1 + dist * Cos(rad)
    ny1 = y1 + dist * Sin(rad)
    
   'addDonutA nx1, ny1
    
    nx2 = x1 + dist * Cos(-rad)
    ny2 = y1 + dist * Sin(-rad)
    
   'addDonutA nx2, ny2
    
    d1 = getDistance(nx1, ny1, x3, y3)
    d2 = getDistance(nx2, ny2, x3, y3)
    
    Debug.Print "D1: " & d1 & ", D2: " & d2
    
    If d1 > d2 Then
        ret = rad
    Else
        ret = -rad
    End If
    
    getRadianValue = ret
    

End Function

Function load_temp()
    Dim selec1 As New ClsSelEntity
    Dim selec2 As New ClsSelEntity
    Dim selec3 As New ClsSelEntity
    
    Dim ss As New clsSelSets
    
    
    Dim pr As New clsPolygonReader
    
    Dim ent As AcadEntity
    Dim b As Boolean
    

    Dim ptd3(2) As Double
    
    Dim ddd As Variant
    
    Dim ent2 As AcadLWPolyline
    Dim dir As String
    Dim rad As Double
    
    
    Dim line As AcadLine
    
    Dim merge As New ClsMerger
    
    Set ent = ss.selectPolyline
    
    
    
    Dim orgsplit() As Double
    Dim newsplit() As Double
    Dim addsplit(3) As Double
    
    Dim dist As Double
    
    rad = 0.01
    
    
    'selec1.selectPolyline ("#Get Polyline 1: ")
    
    'Set ent = selec1.getEntity
    
    ThisDrawing.SetVariable "osmode", 513
    ptd1 = ThisDrawing.Utility.getPoint(, "Enter a point1: ")
    ptd2 = ThisDrawing.Utility.getPoint(, "Enter a point2: ")
   
    pt1.x = ptd1(0)
    pt1.y = ptd1(1)
    pt2.x = ptd2(0)
    pt2.y = ptd2(1)
   
   
    dir = ThisDrawing.Utility.GetString(False, "Direction(F or R)")
    
   
    
    addVertex ent, pt1.x, pt1.y
    addVertex ent, pt2.x, pt2.y
    
    'addDonutA pt1.x, pt1.y
    'addDonutA pt2.x, pt2.y
    
    
    
    pr.init ent
    pr.setIndexByPoint pt1
    pr.setEIndexByPoint pt2
    
    ddd = pr.getShortLine2
    Set ent2 = ThisDrawing.ModelSpace.AddLightWeightPolyline(ddd)
    
    
    d = getDistance(pt1.x, pt1.y, pt2.x, pt2.y)
    m = 1
    
    rad = m / d
    If dir = "F" Or dir = "f" Then
        rad = -1 * rad
    End If
    
    Debug.Print "rad: " & rad
    
    ent.Delete
    
    Set ent = ent2.Copy
    
    ent2.Rotate ptd1, rad
    
    
    orgsplit = ent.Coordinates
    newsplit = ent2.Coordinates
    
    size1 = UBound(orgsplit)
    size2 = UBound(newsplit)
    
    If newsplit(0) = ptd1(0) And newsplit(1) = ptd1(1) Then
    
        ptd3(0) = newsplit(size2 - 1)
        ptd3(1) = newsplit(size2)
    
    Else
        ptd3(0) = newsplit(0)
        ptd3(1) = newsplit(1)
    
    End If
    
    
    'Set line = ThisDrawing.ModelSpace.addLine(ptd2, ptd3)
    
    
    addsplit(0) = ptd3(0)
    addsplit(1) = ptd3(1)
    addsplit(2) = ptd2(0)
    addsplit(3) = ptd2(1)
    
    'line.color = acBlue
     
    'addDonutA ptd3(0), ptd3(1)
    'addDonutA ptd2(0), ptd2(1)
    
    size3 = 4
    
    merge.setSize size1 + size2 + size3 + 1
    
    
    merge.add orgsplit
    merge.add addsplit
    merge.add newsplit
    
    
    ddd = merge.getMerged
    
    ThisDrawing.ModelSpace.AddLightWeightPolyline ddd
    ent.Delete
    ent2.Delete
    
End Function

Attribute VB_Name = "CreateCircle"

Private Const PI As Double = 3.14159265358979
Private Const PI_2 As Double = 1.5707963267949


Sub Createcircle()
    Dim i, ii, x, y As Integer
    Dim FilterType(0) As Integer
    Dim FilterData(0) As Variant
    Dim UsersSelection As AcadSelectionSet
    Dim selObj() As AcadEntity
    Dim ret As Integer
    Dim arcObjs() As AcadEntity
    Dim ddd() As Double
    Dim x2, y2 As Variant
    Dim count As Integer
    Dim newv(0 To 1) As Double
    Dim centerPoint(0 To 2) As Double
    
    Dim returnObj1 As AcadObject
    Dim returnObj3 As AcadObject
    
    With ThisDrawing
        On Error Resume Next
        .SelectionSets("CurrentSelection").Delete
        Set UsersSelection = .SelectionSets.add("CurrentSelece e tion")
        
        
        'ThisDrawing.SetVariable "osmode", 512
        'p1 = ThisDrawing.Utility.GetPoint(, "Enter a point1: ")
        'ThisDrawing.SetVariable "osmode", 0
        'p2 = ThisDrawing.Utility.GetPoint(, "Enter a point2: ")
        'ThisDrawing.SetVariable "osmode", 512
        'p3 = ThisDrawing.Utility.GetPoint(, "Enter a point3: ")
        
        ThisDrawing.SetVariable "osmode", 512
        ThisDrawing.Utility.getEntity returnObj1, p1, "Enter a point 1: "
            
        ThisDrawing.SetVariable "osmode", 1
        p2 = ThisDrawing.Utility.getPoint(, "Enter a point2: ")
        
        ThisDrawing.SetVariable "osmode", 512
        ThisDrawing.Utility.getEntity returnObj3, p3, "Enter a point 3: "
        
        x1 = p1(0)
        y1 = p1(1)
        
        x2 = p2(0)
        y2 = p2(1)
         
        x3 = p3(0)
        y3 = p3(1)
        
        d1 = (x2 - x1) / (y2 - y1)
        d2 = (x3 - x2) / (y3 - y2)
        
        cx = ((y3 - y1) + (x2 + x3) * d2 - (x1 + x2) * d1) / (2 * (d2 - d1))
        cy = -d1 * (cx - (x1 + x2) / 2) + (y1 + y2) / 2
         
        r = VBA.Sqr((x1 - cx) ^ 2 + (y1 - cy) ^ 2)
        
        centerPoint(0) = cx
        centerPoint(1) = cy
        
        ThisDrawing.ModelSpace.AddCircle p1, 0.2
        
        StartAngle = ArcTan2((x1 - cx), (y1 - cy))
        EndAngle = ArcTan2((x3 - cx), (y3 - cy))
        
        
        
        If StartAngle > 0 And EndAngle > 0 Then
            If StartAngle > EndAngle Then
                tmp = StartAngle
                StartAngle = EndAngle
                EndAngle = tmp
            End If
        ElseIf StartAngle < 0 And EndAngle < 0 Then
            If StartAngle > EndAngle Then
                tmp = StartAngle
                StartAngle = EndAngle
                EndAngle = tmp
            End If
        ElseIf StartAngle > 0 And EndAngle < 0 Then
            If StartAngle < PI_2 Then
                tmp = StartAngle
                StartAngle = EndAngle
                EndAngle = tmp
            End If
        ElseIf StartAngle < 0 And EndAngle > 0 Then
            If EndAngle > PI_2 Then
                tmp = StartAngle
                StartAngle = EndAngle
                EndAngle = tmp
            End If
                
        End If
        
        
        
        ThisDrawing.ModelSpace.AddArc centerPoint, r, StartAngle, EndAngle
        
        
        'ThisDrawing.ModelSpace.AddCircle centerPoint, r
         
         
    End With
    
End Sub


   
Function ArcTan2(ByVal x As Double, ByVal y As Double) As Double


    Select Case x
        Case Is > 0
            ArcTan2 = Atn(y / x)
        Case Is < 0
            ArcTan2 = Atn(y / x) + PI * Sgn(y)
            If y = 0 Then ArcTan2 = ArcTan2 + PI
        Case Is = 0
            ArcTan2 = PI_2 * Sgn(y)
    End Select

End Function

Public Function Atn2(ByVal y As Double, ByVal x As Double) As Double

  If x > 0 Then

    Atn2 = Atn(y / x)

  ElseIf x < 0 Then

    Atn2 = Sgn(y) * (PI - Atn(Abs(y / x)))

  ElseIf y = 0 Then

    Atn2 = 0

  Else

    Atn2 = Sgn(y) * PI / 2

  End If

End Function

 


Function getEntitySize(ss As AcadSelectionSet, Text As String) As Integer

    Dim count As Integer
    
    count = 0

    For Each ent In ss
        If ent.ObjectName = Text Then
            count = count + 1
        End If
    Next ent
        
    getEntitySize = count
        


End Function

Attribute VB_Name = "Excutor"
Sub createFillet()

    Dim fillet As New clsFillet
    
    ThisDrawing.EndUndoMark
    ThisDrawing.StartUndoMark
    fillet.load
    
     

End Sub


Sub createFillet2()
    
    Dim fillet2 As New ClsFillet2
        
    
    ThisDrawing.EndUndoMark
    ThisDrawing.StartUndoMark
    
    fillet2.load
    

End Sub


Sub deleteWorkingStuff()

    deleteLayer (TEMP_LAYER)

End Sub




Sub createChamfer()

    Dim chamfer As New ClsChamfer
    
    
    ThisDrawing.EndUndoMark
    ThisDrawing.StartUndoMark
    chamfer.load
    
     

End Sub


Sub createChamfer2()

    Dim chamfer2 As New clsChamfer2
        
    
    ThisDrawing.EndUndoMark
    ThisDrawing.StartUndoMark
    chamfer2.load
     
    

End Sub



Sub revert()

    ThisDrawing.EndUndoMark
    'ThisDrawing.SendCommand "Undo" & vbCr & "Back" & vbCr & "N" & vbCr
    
    
End Sub


Sub createBridge()
    
    Dim pp As New ClsBridge
    pp.createBridge
    
End Sub

Sub showSettingsForm()
    Dim myUserForm As New frmSettings

    myUserForm.frmSettings_init
    myUserForm.show


End Sub



Sub splitBoundary()

    Dim token() As String

    ThisDrawing.StartUndoMark

    saveOnLayers
    hideLayerAll
    
    token = getDefaultLayerOn
    
    showLayerLike token
    
    ThisDrawing.SendCommand "bbc" & vbCr
    
    restoreOnLayers
    
    ThisDrawing.EndUndoMark

End Sub

Sub splitBoundaryEx()
    Dim token() As String
    Dim boundary As New ClsBoundary

    ThisDrawing.StartUndoMark

    saveOnLayers
    hideLayerAll
    
    token = getDefaultLayerOn
    
    showLayerLike token
    
    
    
    boundary.selects
    
    
    
    restoreOnLayers
    
    ThisDrawing.EndUndoMark


End Sub

Sub createTunnel()


    Dim tn As New ClsTunnel
    Dim layers() As String
    
    layers = getDefaultTunnelLayers
    tn.setLayers layers
    tn.load

End Sub


Sub createTunnelEx()

    Dim tn As New ClsTunnel
    Dim layers() As String
    
    tn.loadEx2


End Sub

Sub createWing()
    Dim wn As New ClsWing
    
    wn.load
    

End Sub

Sub cutEntity()
    Dim ce As New ClsBreaker
    
    ce.init
    ce.load
End Sub

Function ArcCos(ByVal x As Double) As Double
  If Abs(Fix(x)) <> 1 Then ''-1<x<1 일때는 계산, x<=-2, x>=2 일때는 오류 발생
    ArcCos = Atn(-x / Sqr(-x * x + 1)) + 2 * Atn(1)
  Else ' -2<x<=-1, 1<=x<2
    If x > 0 Then 'Fix(x)=1일 때 즉 1<=x<2
      ArcCos = 0
    ElseIf x < 0 Then 'Fix(x)=-1일 때 즉 -2<x<=-1
      ArcCos = Atn(1) * 4
    End If
  End If
End Function

Sub createParkinglot()

    Dim cp As New ClsPolylineParkingEx
    Dim rad As Double
    
    
    
    
    'cp.setWidth 5
    
    'rad = PI / 2
    'rad = PI / 3
    
    'cp.setdistance 2.5 / Sin(rad)
    'cp.setParkingLineRotateRadian rad
    cp.load

End Sub

Sub createParkinglotEx()

    Dim pl As New ClsParkingLot
    pl.loadEx
End Sub

Sub unionPolyline()
    Dim up As New ClsUnionPolyline
    
    up.load
    
End Sub


Sub unionPolylineEx()
    Dim up As New ClsUnionPolyline
    
    up.loadEx
    
End Sub



Sub splitPolyline()
    Dim up As New ClsSplitPolyline
    
    up.load
    
End Sub


Sub checkArea()
    Dim ac As New ClsAreaChecker
    
    ac.load
    
End Sub


Sub createOverpassStep()
    Dim ops As New ClsOverpassStep
    
    ops.load
    
End Sub


Sub cutMultiEntity()
    Dim ce As New ClsMultiBreaker
    
    
    ce.load
End Sub

Sub setSnapAngle()
    Dim ort As New ClsSetSnapAng
    
    ort.load
    
End Sub

Sub restoreSnapAngle()
    Dim ort As New ClsSetSnapAng
    
    ort.dispose
    
End Sub

Sub createUndergroundParkingLot()
    Dim ort As New ClsUndergroundParkingLot
    
    ort.loadEx2
    
End Sub


Sub combineNearObject()
    Dim ort As New ClsObjectCombiner

    
    ort.load
    
End Sub


Sub addAptInfo()
    
    Dim ai As New ClsAptInfo
    ai.load

End Sub

Sub addAptPyInfo()
    
    Dim ai As New ClsAptInfo
    ai.loadEx

End Sub



Sub rotateHatch()

    Dim tr As New ClsTextRotater
    tr.rotateHatch

End Sub

Sub rotateText()


    Dim tr As New ClsTextRotater
    tr.rotateText

End Sub


Sub check_mid()

    Dim valid As New ClsValidatorEx
    
    valid.load
    valid.loaddata

End Sub

Sub check_mid__()

    Dim prloader As New ClsPropLoader
    Dim lyr As AcadLayer
    Dim cnt As Integer
    Dim lyrname As String
    Dim lyrname2 As String
    Dim vd As New ClsValidator
    Dim dupcnt As Integer
    Dim duptotal As Integer
    Dim tblpath As String
    
    duptotal = 0
    cnt = ThisDrawing.layers.count
    
    
    tblpath = getMIDTablePropFile
    
    If tblpath <> "" Then
        prloader.load_layer_table tblpath
        
        For i = 0 To cnt - 1
            Set lyr = ThisDrawing.layers.Item(i)
            lyrname = lyr.name
        
            If startsWith(lyrname, "!!변경_") = True Or startsWith(lyrname, "!!삭제_") = True Then
        
                lyrname2 = Replace(lyrname, "!!변경_", "")
                lyrname2 = Replace(lyrname2, "!!추가_", "")
                lyrname2 = Replace(lyrname2, "!!삭제_", "")
                
                
                lyrname2 = prloader.getValue(lyrname2)
                
                'If lyrname2 = "bg_sisul_l" Then
                
                    Debug.Print "============== " & i & "/" & cnt; ") layername: " & lyrname & " >> " & lyrname2
                
                    vd.init lyrname, "Default_" & lyrname2
                    dupcnt = vd.check_mid2
                    duptotal = duptotal + dupcnt
                    ThisDrawing.Utility.prompt lyrname + " 작업완료. 중복:" & dupcnt & vbCrLf
                'End If
            End If
            
            'If i > 50 Then
            '    Exit For
            'End If
            
        Next
        
        ThisDrawing.Utility.prompt "레이어 전체. 중복:" & duptotal & vbCrLf
    End If

End Sub


Sub export_shp()

    Dim se As New ClsShpExporter
    If se.init = True Then
        If se.generate_profile = True Then
            se.exec_profile
        
        End If
    End If

End Sub


Sub export_shp2()

    Dim se As New ClsShpExporter
    'If se.initEx = True Then
    '    If se.generate_profile = True Then
    '        se.exec_profile
    '
    '    End If
    'End If
    
    se.initEx2

End Sub
Sub create_center_text()

    Dim tc As New ClsTextCreator
    tc.load
    
    
End Sub


Sub create_center_text4()

    Dim tc As New ClsTextCreator
    tc.loadEx
    
    
    
End Sub

 


Sub create_center_text6()

    Dim tc As New ClsTextCreator
    tc.loadEx2
    
    
End Sub

Sub test501()

    Dim ploader As New ClsPropLoader
    
    ploader.load_ncode

End Sub

Attribute VB_Name = "ModEntity"
Function polyline2region(ent As AcadEntity) As AcadRegion
    
    Dim reg As AcadRegion
    
    Dim regs() As AcadRegion
    Dim ents() As AcadEntity
     
    Dim ss As Integer
     
    ReDim ents(0) As AcadEntity
    Set ents(0) = ent
    
    On Error GoTo errControl
    regs = ThisDrawing.ModelSpace.AddRegion(ents)
    
    Set polyline2region = regs(0)
    Exit Function
    
errControl:
    
    
    Set polyline2region = Nothing
    
 

End Function

Function polyline2region22(ent As AcadEntity) As AcadRegion
    
    Dim reg As AcadRegion
    
    Dim regs() As AcadRegion
    Dim ents() As AcadEntity
     
    Dim cent As Variant
    Dim pt(2) As Double
    
    ReDim ents(0) As AcadEntity
    Set ents(0) = ent
    
    regs = ThisDrawing.ModelSpace.AddRegion(ents)
    Set reg = regs(0)

    cent = reg.Centroid

    pt(0) = cent(0)
    pt(1) = cent(1)

    ThisDrawing.ModelSpace.AddText "INPUT", pt, 1

    Debug.Print ""
    reg.Delete

End Function

Attribute VB_Name = "ModInit"
Public Const TEMP_LAYER = "temp_layer"
Public Const SHOW_CIRCLE = False

Public Const P2P_TOL = 100    ' 1~100: 1 ------100 민감
Public Const PD_TOL = 0.1     ' 0.1~1: 민감 0.1 ------ 1
Public Const FAR_OVER = 30   '접점이 여러개인데 아주 멀리 떨어진경우를 찾아 skip. () <- 이런경우



Public Const FLT_APT_LAYER = "0,!!추가_BLD_서울_평폴리곤_200113,!!추가_BLD_서울_평폴리곤_200112,!!추가_BLD_부산_평폴리곤_200112,!!추가_BLD_부산_평폴리곤_200113,!!추가_BLD_대구_평폴리곤_200112,!!추가_BLD_대구_평폴리곤_200113," _
                            & "!!추가_BLD_인천_평폴리곤_200112,!!추가_BLD_인천_평폴리곤_200113,!!추가_BLD_광주_평폴리곤_200112,!!추가_BLD_광주_평폴리곤_200113,!!추가_BLD_대전_평폴리곤_200112,!!추가_BLD_대전_평폴리곤_200113," _
                            & "!!추가_BLD_울산_평폴리곤_200112,!!추가_BLD_울산_평폴리곤_200113,!!추가_BLD_세종_평폴리곤_200112,!!추가_BLD_세종_평폴리곤_200113,!!추가_BLD_경기_평폴리곤_200112,!!추가_BLD_경기_평폴리곤_200113," _
                            & "!!추가_BLD_강원_평폴리곤_200112,!!추가_BLD_강원_평폴리곤_200113,!!추가_BLD_충북_평폴리곤_200112,!!추가_BLD_충북_평폴리곤_200113,!!추가_BLD_충남_평폴리곤_200112,!!추가_BLD_충남_평폴리곤_200113," _
                            & "!!추가_BLD_전북_평폴리곤_200112,!!추가_BLD_전북_평폴리곤_200113,!!추가_BLD_전남_평폴리곤_200112,!!추가_BLD_전남_평폴리곤_200113,!!추가_BLD_경북_평폴리곤_200112,!!추가_BLD_경북_평폴리곤_200113," _
                            & "!!추가_BLD_경남_평폴리곤_200112,!!추가_BLD_경남_평폴리곤_200113,!!추가_BLD_제주_평폴리곤_200112,!!추가_BLD_제주_평폴리곤_200113"

Public Const KEY_TOL = "userr1"
Public Const KEY_RAD = "userr2"
Public Const KEY_CHA = "userr3"
Public Const DEF_TOL = 0.1
Public Const DEF_RAD = 3
Public Const DEF_CHA = 3


Public Const KEY_RTMP = "userr5"
Public Const DEF_WING_WIDTH = 1

Public Const KEY_FAR_DIST = "useri1"
Public Const DEF_FAR_DIST = FAR_OVER



Public Const KEY_STMP = "users1"
Public Const DEF_BRD = "RD_SISUL_L_대교_170701"
Public Const DEF_TUN = "RD_SISUL_A_주요터널입구_170404|RD_SISUL_A_주요터널마킹_170405|RD_SISUL_L_주요터널히든선_170407"



Public Const KEY_LAYER_ON = "users4"
Public Const DEF_LAYER_ON = "도로*|!!*|0"

Public Const KEY_TEMP_SPLIT = "users5"
'Public Const KEY_TEMP_SPLIT2 = "users4"
'Public Const DEF_BRD = "RD_SISUL_L_대교_170701"






Public Const LYR_ADD = "!!추가_"
Public Const LYR_DEL = "!!삭제_"


'1: end point
'2: mid point
'32: intersection
'512: nearest












Public Function initConstant()

    Dim tol As Double
    Dim rad As Double
    Dim fardist As Integer
    
    tol = ThisDrawing.GetVariable(KEY_TOL)
    rad = ThisDrawing.GetVariable(KEY_RAD)
    fardist = ThisDrawing.GetVariable(KEY_FAR_DIST)


    If tol = 0 Then
        tol = DEF_TOL
        ThisDrawing.SetVariable KEY_TOL, tol
    End If


    If rad = 0 Then
        rad = DEF_RAD
        ThisDrawing.SetVariable KEY_RAD, rad
    End If


    If fardist = 0 Then
        fardist = DEF_FAR_DIST
        ThisDrawing.SetVariable KEY_FAR_DIST, fardist
    End If


End Function


Public Function setDefaultFilletRadius(rad As Double)

    ThisDrawing.SetVariable KEY_RAD, rad

End Function

Public Function getDefaultFilletRadius() As Double

    Dim rad As Double
    rad = ThisDrawing.GetVariable(KEY_RAD)
    
    If rad = 0 Then
        rad = DEF_RAD
        ThisDrawing.SetVariable KEY_RAD, rad
    End If
    
    getDefaultFilletRadius = rad
    
End Function


Public Function setDefaultTolerance(tol As Double)

    ThisDrawing.SetVariable KEY_TOL, tol

End Function


Public Function getDefaultTolerance()

    Dim tol As Double
    tol = ThisDrawing.GetVariable(KEY_TOL)
   
    If tol = 0 Then
        tol = DEF_TOL
        ThisDrawing.SetVariable KEY_TOL, tol
    End If

    getDefaultTolerance = tol
    
End Function


Public Function setDefaultChamferDistance(cd As Double)

    ThisDrawing.SetVariable KEY_CHA, cd

End Function


Public Function getDefaultChamferDistance()

    Dim cd As Double
    cd = ThisDrawing.GetVariable(KEY_CHA)
   
    If cd = 0 Then
        cd = DEF_CHA
        ThisDrawing.SetVariable KEY_CHA, cd
    End If

    getDefaultChamferDistance = cd
    
End Function


Public Function getDefaultWingWidth() As Double

    Dim rad As Double
    rad = ThisDrawing.GetVariable(KEY_RTMP)
    
    If rad = 0 Then
        rad = DEF_WING_WIDTH
        ThisDrawing.SetVariable KEY_RTMP, rad
    End If
    
    getDefaultWingWidth = rad
    
End Function


Public Function setDefaultFarDistance(cd As Double)

    ThisDrawing.SetVariable KEY_FAR_DIST, cd

End Function


Public Function getDefaultFarDistance()

    Dim cd As Double
    cd = ThisDrawing.GetVariable(KEY_FAR_DIST)
   
    If cd = 0 Then
        cd = DEF_FAR_DIST
        ThisDrawing.SetVariable KEY_FAR_DIST, cd
    End If

    getDefaultFarDistance = cd
    
End Function



Public Function setDefaultBridgeLayer(layer As String)

    ThisDrawing.SetVariable KEY_STMP, layer

End Function

Public Function getDefaultBridgeLayer() As String

    Dim layer As String
    layer = ThisDrawing.GetVariable(KEY_STMP)
    
    If layer = Empty Then
        layer = DEF_BRD
        ThisDrawing.SetVariable KEY_STMP, layer
    End If
    
    getDefaultBridgeLayer = layer
    
End Function


Public Function setDefaultTunnelLayers(layer As String)

    ThisDrawing.SetVariable KEY_STMP, layer

End Function

Public Function getDefaultTunnelLayers() As String()

    Dim layer As String
    Dim layers() As String
    layer = ThisDrawing.GetVariable(KEY_STMP)
    
    If layer = Empty Then
        layer = DEF_TUN
        ThisDrawing.SetVariable KEY_STMP, layer
    End If
    
    layers() = Split(layer, "|")
    
    getDefaultTunnelLayers = layers
    
End Function


Public Function setDefaultLayerOn(layer As String)

    ThisDrawing.SetVariable KEY_LAYER_ON, layer

End Function

Public Function getDefaultLayerOn() As String()

    Dim layer As String
    Dim layers() As String
    layer = ThisDrawing.GetVariable(KEY_LAYER_ON)
    
    If layer = Empty Then
        layer = DEF_LAYER_ON
        ThisDrawing.SetVariable KEY_LAYER_ON, layer
    End If
    
    
    layers() = Split(layer, "|")
        
    getDefaultLayerOn = layers
    
End Function


Public Function getDefaultLayerOnString() As String

    Dim layer As String

    layer = ThisDrawing.GetVariable(KEY_LAYER_ON)
    
    If layer = Empty Then
        layer = DEF_LAYER_ON
        ThisDrawing.SetVariable KEY_LAYER_ON, layer
    End If
    
        
    getDefaultLayerOnString = layer
    
End Function



Public Function setTempSplit(result As String)  '1|2|3|

    ThisDrawing.SetVariable KEY_TEMP_SPLIT, result

End Function


Public Function getTempSplit() As String()

    Dim str() As String
    Dim result As String
    result = ThisDrawing.GetVariable(KEY_TEMP_SPLIT)
    
    If result <> Empty Then
        str() = Split(result, "|")
        
    End If
    
    getTempSplit = str
    
End Function

Attribute VB_Name = "ModPath"
Public Const SETDIR = "C:\CADSET"




Public Function isExistsFile(strpath As String) As Boolean
    Dim ret As Boolean
    
    
    ret = True
    Set fso = CreateObject("Scripting.FileSystemObject")
    
    If fso.FileExists(strpath) = False Then
    
        'write_file ("여기에 " & strpath & " 파일을 만들어야 합니다")
        MsgBox strpath & vbCrLf & "파일을 찾을 수 없습니다."
        
        ret = False
    End If
    
    isExistsFile = ret


End Function


Public Function isExistsFileEx(strpath As String, bshow As Boolean) As Boolean
    Dim ret As Boolean
    
    
    ret = True
    Set fso = CreateObject("Scripting.FileSystemObject")
    
    If fso.FileExists(strpath) = False And bshow = True Then
    
        'write_file ("여기에 " & strpath & " 파일을 만들어야 합니다")
        MsgBox strpath & vbCrLf & "파일을 찾을 수 없습니다."
        
        ret = False
    End If
    
    isExistsFileEx = ret


End Function

Public Function getShpExportPropFile() As String
    Dim basepath As String

    basepath = getSettingDir & "\" & "EPSLIST.txt"
    
    If isExistsFile(basepath) = False Then
    
        basepath = ""
    
    End If
    
    getShpExportPropFile = basepath


End Function


Public Function getHatchPatternAnglePropFile() As String
    Dim basepath As String

    basepath = getSettingDir & "\" & "$CAD_HATCH_ANGLE.txt"
    
    If isExistsFileEx(basepath, False) = False Then
    
        basepath = ""
    
    End If
    
    getHatchPatternAnglePropFile = basepath


End Function

Public Function getShpExportLayerPropFile() As String
    Dim basepath As String

    basepath = getSettingDir & "\" & "CAD_SHP_EXPORT_LAYER.txt"
    
    If isExistsFile(basepath) = False Then
    
        basepath = ""
    
    End If
    
    getShpExportLayerPropFile = basepath


End Function

Public Function getShpExportLayer2PropFile() As String
    Dim basepath As String

    basepath = getSettingDir & "\" & "CAD_SHP_EXPORT_LAYER_TYPE2.txt"
    
    If isExistsFile(basepath) = False Then
    
        basepath = ""
    
    End If
    
    getShpExportLayer2PropFile = basepath


End Function



Public Function getNcodeSec2PropFile() As String
    Dim basepath As String

    basepath = getSettingDir & "\" & "CAD_NCODE_SEC2.txt"
    
    If isExistsFile(basepath) = False Then
    
        basepath = ""
    
    End If
    
    getNcodeSec2PropFile = basepath
 

End Function


Public Function getMIDTablePropFile() As String
    Dim basepath As String

    basepath = getSettingDir & "\" & "CAD_CHECK_MID_LAYER.txt"
    
    If isExistsFile(basepath) = False Then
    
        basepath = ""
    
    End If
    
    getMIDTablePropFile = basepath

End Function


Public Function getProfilePropFile() As String
    Dim basepath As String

    basepath = getSettingDir & "\" & "dawul_profile.epf"
    
    If isExistsFile(basepath) = False Then
    
        basepath = ""
    
    End If
    
    getProfilePropFile = basepath

End Function


Public Function getExecProfilePropFile() As String
    Dim basepath As String

    basepath = getSettingDir & "\" & "exec_profile.epf"
    
    getExecProfilePropFile = basepath

End Function


Public Function getShpFilePath() As String
    Dim basepath As String
    
    basepath = getSettingDir & "\" & "SHPEXPORT_" & Format(Now, "yyyyMMdd_hhmmss")

    Set fso = CreateObject("Scripting.FileSystemObject")
    If fso.FolderExists(basepath) = False Then
        MkDir basepath
    End If
  
    getShpFilePath = basepath

End Function

Public Function getShpExtFilePath(rootpath As String, subs As String) As String
    Dim basepath As String
    
    basepath = rootpath & "\" & subs

    Set fso = CreateObject("Scripting.FileSystemObject")
    If fso.FolderExists(basepath) = False Then
        MkDir basepath
    End If
  
    getShpExtFilePath = basepath

End Function



Function getSettingDir() As String
 
    Dim basepath As String

    'basepath = CurDir$ & "\" & SETDIR
    basepath = SETDIR
    
    Set fso = CreateObject("Scripting.FileSystemObject")
    If fso.FolderExists(basepath) = False Then
        MkDir basepath
    End If
    
    getSettingDir = basepath

End Function



Function write_file(strpath As String)

    Dim fso As Object
    
    Set fso = CreateObject("Scripting.FileSystemObject")
    Dim oFile As Object
    Set oFile = fso.CreateTextFile(strpath)
    oFile.WriteLine "KEY,VALUE"
    oFile.Close
    Set fso = Nothing
    Set oFile = Nothing
End Function

Attribute VB_Name = "ModProp"
Function createODTable()

    Dim acadObj1 As Object
    Dim acadObj2 As Object
    
    Dim odinfo1 As New ClsODInfo
    Dim odinfo2 As New ClsODInfo
    
    Dim col As New Collection

    Set acadObj1 = selectEntity()
    Set acadObj2 = selectEntity()
    
    hasTablename acadObj1
    
    
    odinfo1.init acadObj1, "SampleOD3"
    odinfo1.setODFieldDefs
    odinfo1.setTableInstance
    
    Set col = odinfo1.getInfo
    
    odinfo2.init acadObj2, "SampleOD3"
    odinfo2.setODFieldDefs
    odinfo2.setTableInstance
    
    'col.add "test"
    'col.add 1
    'col.add "0"
    
    odinfo2.setInfo col
    

End Function


Function hasTablename(acadObj As Object) As String

    Dim amap As AutocadMAP.AcadMap
    Dim proj As AutocadMAP.Project
    
    Dim odrecrds As ODRecords
    Dim odrecrd As ODRecord
    
    Dim tbl As ODTable
    Dim bb As Boolean
    
    Dim tblname As String
    Dim temp As Variant
    
    On Error GoTo toEnd
    
    Set amap = ThisDrawing.Application.GetInterfaceObject("AutoCADMap.Application")
    Set proj = amap.Projects(ThisDrawing)

    For Each tbl In proj.ODTables
        Set odrecrds = tbl.GetODRecords
        odrecrds.init acadObj, False, False
        
        Set temp = tbl.ODFieldDefs
        
        bb = odrecrds.IsDone
        
        If bb = False Then
            'Debug.Print "FOUND >>>>> " & tbl.name
            tblname = tbl.name
        Else
            'Debug.Print "NOT FOUND >>>>> " & tbl.name
        End If
    
        
    Next
    
toEnd:
    
    hasTablename = tblname
    
End Function

Function isTableExists(tblname As String) As Boolean

    Dim bret As Boolean
    
    Dim amap As AutocadMAP.AcadMap
    Dim proj As AutocadMAP.Project
    Dim tbl As AutocadMAP.ODTable
    
    Set amap = ThisDrawing.Application.GetInterfaceObject("AutoCADMap.Application")
    Set proj = amap.Projects(ThisDrawing)
    
    For Each tbl In proj.ODTables
        If UCase(tbl.name) = UCase(tblname) Then
            isTableExists = True
            Exit Function
        End If
    Next
    
    isTableExists = False
 

End Function

Function createAptODBTable(tblname As String) As Boolean

    Dim tbldesc As String
    Dim cmd As String
    Dim bret As Boolean

    tbldesc = "호수정보"
    bret = True

    If isTableExists(tblname) = False Then
        cmd = "(setq tabldefn " _
            & "'((""tablename"" . """ & tblname & """) " _
            & "  (""tabledesc"" . """ & tbldesc & """) " _
            & "  (""columns""" _
            & "    ((""colname"" . ""층수"") " _
            & "     (""coldesc"" . ""층수"") " _
            & "     (""coltype"" . ""integer"") " _
            & "     (""defaultval"" . 0))" _
            & "    ((""colname"" . ""호수"") " _
            & "     (""coldesc"" . ""호수"") " _
            & "     (""coltype"" . ""integer"") " _
            & "     (""defaultval"" . 0))" _
            & "  )))"
    
        ThisDrawing.SendCommand cmd & vbCr
        ThisDrawing.SendCommand "(ade_oddefinetab tabldefn)" & vbCr
    
    End If
            
    If isTableExists(tblname) = False Then
        MsgBox "예기치않은 오류가 발생했습니다. 개발자에게 문의하세요."
        bret = False
    End If

    createAptODBTable = bret

End Function


Function createAptPyODBTable(tblname As String) As Boolean

    Dim tbldesc As String
    Dim cmd As String
    Dim bret As Boolean

    tbldesc = "아파트평정보"
    bret = True

    If isTableExists(tblname) = False Then
        cmd = "(setq tabldefn " _
            & "'((""tablename"" . """ & tblname & """) " _
            & "  (""tabledesc"" . """ & tbldesc & """) " _
            & "  (""columns""" _
            & "    ((""colname"" . ""공급면적"") " _
            & "     (""coldesc"" . ""공급면적"") " _
            & "     (""coltype"" . ""real"") " _
            & "     (""defaultval"" . 0))" _
            & "    ((""colname"" . ""전용면적"") " _
            & "     (""coldesc"" . ""전용면적"") " _
            & "     (""coltype"" . ""real"") " _
            & "     (""defaultval"" . 0))" _
            & "  )))"
    
        ThisDrawing.SendCommand cmd & vbCr
        ThisDrawing.SendCommand "(ade_oddefinetab tabldefn)" & vbCr
    
    End If
            
    If isTableExists(tblname) = False Then
        MsgBox "예기치않은 오류가 발생했습니다. 개발자에게 문의하세요."
        bret = False
    End If

    createAptPyODBTable = bret

End Function


Private Function getTableInstance(proj As AutocadMAP.Project, ODfdfs As ODFieldDefs, tblname As String) As ODTable
    Dim tbl As AutocadMAP.ODTable
    For Each tbl In proj.ODTables
        If UCase(tbl.name) = UCase(tblname) Then
            Set getTableInstance = tbl
            Exit Function
        End If
    Next
    
    Set tbl = proj.ODTables.add(tblname, "Sample Xdata", ODfdfs, True)
    
    Set getTableInstance = tbl

End Function



Private Function HasTable(proj As AutocadMAP.Project, tblname As String) As Boolean
    Dim tbl As AutocadMAP.ODTable
    For Each tbl In proj.ODTables
        If UCase(tbl.name) = UCase(tblname) Then
            HasTable = True
            Exit Function
        End If
    Next
    HasTable = False
End Function


Function hasProperties(ent As AcadEntity) As Boolean

    Dim adic As AcadDictionary
    Dim ret As Boolean
    
    
    ret = ent.HasExtensionDictionary
    
    If ret = True Then
    
        Set adic = ent.GetExtensionDictionary()
        If adic.count <= 0 Then
            ret = False
        End If
    
    End If
    
    hasProperties = ret
    

End Function


Function hasODTableProperties(ent As AcadEntity, tblname As String) As Boolean

    Dim adic As AcadDictionary
    Dim obj As AcadObject
    Dim ret As Boolean
    
    
    ret = ent.HasExtensionDictionary
    
    If ret = True Then
    
        Set adic = ent.GetExtensionDictionary()
        For i = 0 To adic.count
        
            Set obj = adic.Item(0)
            Debug.Print ""
        
        Next
        
    End If
    
    hasODTableProperties = ret
    

End Function


Sub show_properties()

    Dim ent As AcadEntity
    Dim tbls As ODTables
    Dim tbl As ODTable
    Dim recrds As ODRecords
    
    Dim recrd As ODRecord
    Dim fieldv As odfieldvalue
    
    Dim fieldds As ODFieldDefs
    Dim fieldd As ODFieldDef
        
    Dim amap As AcadMap
    Dim layername As String
    Dim xdata As Variant
    
    Dim adic As AcadDictionary
    Dim vvv As Variant
    
    
    
    Set ent = selectEntity()
    
    Set amap = ThisDrawing.Application.GetInterfaceObject("AutoCADMap.Application")
    Set tbls = amap.Projects(ThisDrawing).ODTables
    
    
    layername = ent.layer
    Debug.Print ent.ObjectName & " " & ent.ObjectID & " " & ent.OwnerID & " " & ent.PlotStyleName
    Debug.Print " " & ent.HasExtensionDictionary
    
    
    Set adic = ent.GetExtensionDictionary()
    If adic.count > 0 Then
    
        Set vvv = adic.Item(0)
        
            
        Dim xdataOut As Variant
        Dim xtypeOut As Variant
        ent.GetXData "", xtypeOut, xdataOut
        
        'layername = "bg_rd_walk_l"
        
        For Each tbl In tbls
                
Try:
            On Error GoTo Catch
            
            Set odrecrds = tbl.GetODRecords
            odrecrds.init ent, True, False
            
            If odrecrds.IsDone = False Then
                Set odrecrd = odrecrds.record
                Set fieldds = tbl.ODFieldDefs
                
                count = fieldds.count
                
                
                For i = 0 To count - 1
                    Set fieldd = fieldds.Item(i)
                    Set fieldv = odrecrd.Item(i)
                
                    Debug.Print i & ")" & fieldd.name & ": " & fieldv.value
                
                Next
            End If
          
            GoTo Finally
Catch:
    
Finally:
            
        Next
    End If
    
End Sub

Sub show_properties_old()

    Dim ent As AcadEntity
    Dim tbls As ODTables
    Dim tbl As ODTable
    Dim recrds As ODRecords
    
    Dim recrd As ODRecord
    Dim fieldv As odfieldvalue
    
    Dim fieldds As ODFieldDefs
    Dim fieldd As ODFieldDef
        
    Dim amap As AcadMap
    Dim layername As String
    Dim xdata As Variant
    
    Dim adic As AcadDictionary
    Dim vvv As Variant
    
    
    
    Set ent = selectEntity()
    
    Set amap = ThisDrawing.Application.GetInterfaceObject("AutoCADMap.Application")
    Set tbls = amap.Projects(ThisDrawing).ODTables
    
    
    layername = ent.layer
    Debug.Print ent.ObjectName & " " & ent.ObjectID & " " & ent.OwnerID & " " & ent.PlotStyleName
    Debug.Print " " & ent.HasExtensionDictionary
    
    
    Set adic = ent.GetExtensionDictionary()
    Set vvv = adic.Item(0)
    
        
    Dim xdataOut As Variant
    Dim xtypeOut As Variant
    ent.GetXData "", xtypeOut, xdataOut
    
    layername = "bg_rd_width_sudo_"
    
    For Each tbl In tbls
    
        Debug.Print ">>>>>>>>>> " & tbl.name & " " & tbl.Description
        
    
        If tbl.name = "Default_" & layername Then
            Set odrecrds = tbl.GetODRecords
            odrecrds.init ent, True, False
            
            Set odrecrd = odrecrds.record
            Set fieldds = tbl.ODFieldDefs
            
            count = fieldds.count
            
            
            For i = 0 To count - 1
                Set fieldd = fieldds.Item(i)
                Set fieldv = odrecrd.Item(i)
            
                Debug.Print i & ")" & fieldd.name & ": " & fieldv.value
            
            Next
             
        End If
    Next
    
End Sub

Attribute VB_Name = "ModString"
Public Function EndsWith(str As String, ending As String) As Boolean
     Dim endingLen As Integer
     endingLen = Len(ending)
     EndsWith = (Right(Trim(UCase(str)), endingLen) = UCase(ending))
End Function

Public Function startsWith(str As String, start As String) As Boolean
     Dim startLen As Integer
     startLen = Len(start)
     startsWith = (Left(Trim(UCase(str)), startLen) = UCase(start))
End Function

Attribute VB_Name = "Module1"
Option Explicit
Function PolyCoords(oEnt As AcadEntity) As Variant
    Dim cnt As Integer
    Dim i As Integer
    Dim j As Integer
    Dim iStep As Integer
    Dim varPt As Variant
    Dim dblCoords() As Double
    Dim dblVert() As Double

    If TypeOf oEnt Is AcadLWPolyline Then
         iStep = 2
    ElseIf TypeOf oEnt Is Acad3DPolyline Or _
           TypeOf oEnt Is AcadPolyline Then
         iStep = 3
    End If
    dblCoords = oEnt.Coordinates

    ReDim ptsArr(0 To (UBound(dblCoords) + 1) \ iStep - 1, 0 To iStep - 1) As Double
    For i = 0 To (UBound(dblCoords) + 1) \ iStep - 1
         For j = 0 To iStep - 1
              ptsArr(i, j) = dblCoords(cnt)
              Debug.Print ptsArr(i, j)
              cnt = cnt + 1
         Next
    Next
    PolyCoords = ptsArr
End Function

Function Step2(pt1 As Variant) As Variant

    Dim UsersSelection As AcadSelectionSet
    Dim coord() As Double
    Dim sel As AcadEntity
    
    Dim ent As AcadEntity
    Dim plieObj As AcadPolyline
    

    Dim position(0 To 2) As Double
    With ThisDrawing
        On Error Resume Next
        .SelectionSets("CurrentSelection").Delete
        Set UsersSelection = .SelectionSets.add("CurrentSelection")
        UsersSelection.SelectAtPoint (pt1)
     
        Set sel = UsersSelection.Item(0)
        'sel.color = acBlue
        
        'createPolygon (sel.Coordinates)
            
        Set plieObj = ThisDrawing.ModelSpace.AddPolyline(sel.Coordinates)
        
        plieObj.color = arBlue
        
        MsgBox UsersSelection.name
     
    End With
    
    
End Function


Function createPolygon(verlist As Double)

    Dim obj As AcadPolyline
    
    
    obj = ThisDrawing.ModelSpace.AddPolyline(verlist)
    obj.color = arBlue

End Function


Sub demo()
    Dim pts As Variant
    Dim varPt As Variant
    Dim oEnt As AcadEntity
    Dim returnPnt As Variant
    
    Dim returnObj1 As AcadObject
    Dim basePnt1 As Variant
    
    Dim returnObj2 As AcadObject
    Dim basePnt2 As Variant
    
    Dim startPoint(0 To 2) As Double
    Dim endPoint(0 To 2) As Double
    
    Dim plist() As Double
    
    ' Return a point using a prompt
    basePnt1 = ThisDrawing.Utility.getPoint(, "Enter a point1: ")
    basePnt2 = ThisDrawing.Utility.getPoint(, "Enter a point2: ")
    'ThisDrawing.Utility.GetEntity returnObj1, basePnt1, "enter a point1"
    'ThisDrawing.Utility.GetEntity returnObj2, basePnt2, "enter a point2"
    
    
    Step2 (basePnt1)
    ThisDrawing.ModelSpace.addLine basePnt1, basePnt2
    ThisDrawing.ModelSpace.add
    
    
    
    
   
    
    
    'pts = step(oEnt)
End Sub

Attribute VB_Name = "Module2"
Function Step2(pt1 As Variant) As Variant

    Dim UsersSelection As AcadSelectionSet
    Dim coord() As Double
    Dim sel As AcadEntity
    
    Dim ent As AcadEntity
    Dim plieObj As AcadPolyline
    

    Dim position(0 To 2) As Double
    With ThisDrawing
        On Error Resume Next
        .SelectionSets("CurrentSelection").Delete
        Set UsersSelection = .SelectionSets.add("CurrentSelection")
        UsersSelection.SelectAtPoint (pt1)
     
        Set sel = UsersSelection.Item(0)
        'sel.color = acBlue
        
        'createPolygon (sel.Coordinates)
            
        Set plieObj = ThisDrawing.ModelSpace.AddPolyline(sel.Coordinates)
        
        plieObj.color = arBlue
        
        MsgBox UsersSelection.name
     
    End With
    
    
End Function


Sub arc2lines()

    Dim myArc As AcadArc
    Dim objSel As AcadEntity
    Dim myPL As AcadLWPolyline
    Dim mypolarpoint
    Dim Bulge() As Double
    Dim legs As Integer
    Const PI = 3.14159265358979
    Dim delta As Double
    
    ThisDrawing.Utility.getEntity objSel, returnObj, "Select Arc:"
    If objSel.ObjectName = "AcDbArc" Then
        Set myArc = objSel
        arc2line myArc
    End If

End Sub

Attribute VB_Name = "Module3"


Function addFilletArcline()

    ThisDrawing.SetVariable "osmode", 512
    ThisDrawing.Utility.getEntity returnObj1, tmp, "Enter a point 1: "
        
    p1(0) = tmp(0)
    p1(1) = tmp(1)
        
    ThisDrawing.SetVariable "osmode", 0
    p2 = ThisDrawing.Utility.getPoint(, "Enter a point2: ")
     
    ThisDrawing.SetVariable "osmode", 512
    ThisDrawing.Utility.getEntity returnObj3, tmp, "Enter a point 3: "
    
    p3(0) = tmp(0)
    p3(1) = tmp(1)
    
    
    Set retArc = getArcBy3P(p1, p2, p3) '세점을 지나는 아크를 생성
    
    
    Set addFilletArcline = arc2line(retArc)  '아크를 라인으로 변경

End Function

 





Function mergeAll(d1() As Double, d2() As Double, d3() As Double, d4() As Double) As Double()

    Dim dout() As Double
    Dim count As Integer
    Dim reverse As Boolean
    
    
    reverse = False
    
    'count = UBound(d1) + UBound(d2) + 3 - 2
    'count = UBound(d1) + UBound(d2) + UBound(d3) + 4 - 2
    count = UBound(d1) + UBound(d2) + UBound(d3) + UBound(d4) + 1 - 2
    
    ReDim dout(count) As Double
    
    idx = 0
    
    For i = 0 To UBound(d1)
        dout(idx) = d1(i)
        idx = idx + 1
    Next
    
    
    addDonut3 d1(0), d1(1)
    addDonut3 dout(idx - 2), dout(idx - 1)
    
    If d2(0) = d1(UBound(d1) - 1) Then
        reverse = False
    Else
        reverse = True
    End If
    
    If reverse = False Then
        For i = 2 To UBound(d2) Step 2
            dout(idx) = d2(i)
            idx = idx + 1
            dout(idx) = d2(i + 1)
            idx = idx + 1
            addDonut3 dout(idx - 2), dout(idx - 1)
        Next
        
    Else
        For i = UBound(d2) - 3 To 0 Step -2
            dout(idx) = d2(i)
            idx = idx + 1
            dout(idx) = d2(i + 1)
            idx = idx + 1
            addDonut3 dout(idx - 2), dout(idx - 1)
        Next
    End If
        
    If reverse = False Then
        For i = 2 To UBound(d3) Step 2
            dout(idx) = d3(i)
            idx = idx + 1
            dout(idx) = d3(i + 1)
            idx = idx + 1
            addDonut3 dout(idx - 2), dout(idx - 1)
     
        Next
    Else
        For i = UBound(d3) - 1 To 0 Step -2
            dout(idx) = d3(i)
            idx = idx + 1
            dout(idx) = d3(i + 1)
            idx = idx + 1
            addDonut3 dout(idx - 2), dout(idx - 1)
        Next
    End If
    
    If d3(0) = d2(UBound(d2) - 1) Then
        reverse = Not reverse
    Else
        reverse = reverse
    End If
    
    If reverse = True Then 'd3(0) = d2(UBound(d2) - 1)
        For i = 2 To UBound(d4) Step 2
            dout(idx) = d4(i)
            idx = idx + 1
            dout(idx) = d4(i + 1)
            idx = idx + 1
            addDonut3 dout(idx - 2), dout(idx - 1)
        Next
    Else
        For i = UBound(d4) - 1 To 0 Step -2
            dout(idx) = d4(i)
            idx = idx + 1
            dout(idx) = d4(i + 1)
            idx = idx + 1
            addDonut3 dout(idx - 2), dout(idx - 1)
        Next
    End If
    
     
    'addDonut3 d4(0), d4(1)
    'addDonut3 dout(idx - 2), dout(idx - 1)

    
    
    
    mergeAll = dout
    
    

End Function



Function searchInnerLine(plObj As AcadEntity, f1obj As AcadEntity, f2obj As AcadEntity) As Double()
    searchInnerLine = searchCrossLine(plObj, f1obj, f2obj, True)
End Function

Function searchOutLine(plObj As AcadEntity, f1obj As AcadEntity, f2obj As AcadEntity) As Double()

    searchOutLine = searchCrossLine(plObj, f1obj, f2obj, False)

End Function


Function searchCrossLine(plObj As AcadEntity, f1obj As AcadEntity, f2obj As AcadEntity, isinner As Boolean) As Double()

    Dim dpl() As Double
    Dim df1() As Double
    Dim df2() As Double
    Dim point As Double
    
    Dim f1idx, f1idxn As Integer    '필렛1 접점 인덱스
    Dim f2idx, f2idxn As Integer    '필렛2 접점 인덱스
    
    Dim index1, index1n As Integer   '폴리라인 접점 인덱스
    
    
    Dim dret() As Double    '리턴좌표
    Dim itotal As Integer
    
    'Set ret = Nothing
    
    dpl = plObj.Coordinates '폴리라인
    df1 = f1obj.Coordinates '필렛1
    df2 = f2obj.Coordinates '필렛2

    x = df1(0)
    y = df1(1)
    
    
    index1 = searchIndex(dpl, x, y)
    
    If index1 = -1 Then
        count = UBound(df1)
        
        x = df1(count - 1)
        y = df1(count)
        
        index1 = searchIndex(dpl, x, y)
        f1idx = count - 1
        f1idxn = count - 3
    Else
        f1idx = 0
        f1idxn = 2
        
    
    End If
    
    x = df2(0)
    y = df2(1)
    
    index2 = searchIndex(dpl, x, y)
    
    If index2 = -1 Then
        count = UBound(df2)
        
        x = df2(count - 1)
        y = df2(count)
        
        index2 = searchIndex(dpl, x, y)
        f2idx = count - 1
        f2idxn = count - 3
    Else
        f2idx = 0
        f2idxn = 2
    End If
    


    If index1 + 2 > UBound(dpl) Then
        index1n = index1 - 2
    Else
        index1n = index1 + 2
    End If


    cx = dpl(index1)
    cy = dpl(index1 + 1)
    
    x1 = dpl(index1n)
    y1 = dpl(index1n + 1)
    
    x2 = df1(f1idxn)
    y2 = df1(f1idxn + 1)

    'addDonut3 cx, cy
    'addDonut3 x1, y1
    'addDonut3 x2, y2
    


    rad = Abs(Atn((y2 - cy) / (x2 - cx)) - Atn((y1 - cy) / (c1 - cx)))
    
    
    
    If (rad < 1.571) = isinner Then '삭제영역에 해당함
    
        itotal = UBound(dpl)
        If index2 = 0 Then
            index2 = itotal
        End If
        
        If index2 > index1 Then     '올바른 방향임
            count = index2 - index1 + 2
            ReDim dret(0 To count) As Double
            
            idx = 0
            
            For i = index1 To index2 + 2 Step 2
            
                If i > itotal Then
                    dret(idx) = dpl(i - (itotal + 1))
                    idx = idx + 1
                    dret(idx) = dpl(i - (itotal + 1) + 1)
                    idx = idx + 1
                Else
                    dret(idx) = dpl(i)
                    idx = idx + 1
                    dret(idx) = dpl(i + 1)
                    idx = idx + 1
                End If
            
                'addDonut3 dret(idx - 2), dret(idx - 1)
            Next
        
        Else
            count = index1 - index2 + 1
            ReDim dret(0 To count) As Double
            
            idx = 0
            
            For i = index2 To index1 + 1 Step 2
                dret(idx) = dpl(i)
                idx = idx + 1
                dret(idx) = dpl(i + 1)
                idx = idx + 1
            Next
            'count = index1 - index2 + 1
            'ReDim dret(0 To count) As Double
            
            'idx = 0
            'For i = index1 To index2 Step -2
            '   dret(idx) = dpl(i)
            '   idx = idx + 1
            '   dret(idx) = dpl(i + 1)
            '   idx = idx + 1
            '   addDonut3 dpl(i), dpl(i + 1)
            
            'Next
         
        
        End If
        
    Else
        If index2 > index1 Then
        
            count = index1 + UBound(dpl) - index2 + 2   'y좌표 2개라서 +2
            ReDim dret(0 To count) As Double
            idx = 0
        
            For i = index2 To UBound(dpl)   '개수만큼 찾기때문에 y가 포함됨 +1 안함
                dret(idx) = dpl(i)
                idx = idx + 1
            Next
                    
            For i = 0 To index1 + 1 'y좌표 포함해야하므로 +1
                dret(idx) = dpl(i)
                idx = idx + 1
            Next
            
             
            
        Else
        
        End If
    
    End If
    
    
    
    searchCrossLine = dret
    

End Function

Function searchIndex(d() As Double, ByVal x As Double, ByVal y As Double) As Integer

    Dim index As Integer
    
    index = -1
    
    For i = 0 To UBound(d) Step 2
    
        If d(i) = x And d(i + 1) = y Then
            index = i
        End If
    
    Next


    searchIndex = index
    
End Function


 



 

Sub SelectRawData()
    Dim i, ii, x, y As Integer
    Dim FilterType(0) As Integer
    Dim FilterData(0) As Variant
    Dim UsersSelection As AcadSelectionSet
    Dim selObj() As AcadEntity
    Dim ret As Integer
    Dim arcObjs() As AcadEntity
    Dim ddd() As Doubleos
    Dim x2, y2 As Variant
    Dim count As Integer
    Dim newv(0 To 1) As Double
    
    ThisDrawing.SetVariable "osmode", 512
    
    With ThisDrawing
        On Error Resume Next
        .SelectionSets("CurrentSelection").Delete
        Set UsersSelection = .SelectionSets.add("CurrentSelection")
        
        
        FilterType(0) = 0
        FilterData(0) = "LWPolyline"
        
        UsersSelection.SelectOnScreen FilterType, FilterData
        
        
        count = getEntitySize(UsersSelection, "AcDbPolyline") - 1 'AcDbArc
        
        ReDim selObj(0 To count) As AcadEntity
        
        For i = 0 To count
            Set selObj(i) = UsersSelection.Item(i)
              
        Next i
        
        
    End With
    
    
    vx = 1194.35534891423
    vy = 2999.85414787302
    newv(0) = vx: newv(1) = vy
    
    For i = 0 To count
        ddd = selObj(i).Coordinates
        count = UBound(ddd)
        
        x1 = ddd(count - 1)
        y1 = ddd(count)
        
        For ii = 0 To count Step 2
        
            x2 = ddd(ii)
            y2 = ddd(ii + 1)
            
            f = (y2 - y1) / (x2 - x1)
            
            f1 = (vy - y1) / (vx - x1)
            f2 = (y2 - vy) / (x2 - vx)
            
            If Abs(f1 - f2) < 0.00001 Then
                addDonut x2, y2
                addDonut x1, y1
                
                selObj(i).addVertex ii / 2, newv
                selObj(i).Update
            
            End If
            
            x1 = x2
            y1 = y2
            
        Next ii
    Next i
     
    
    
End Sub


 


Sub test()
    
    Dim SelPl(0 To 1) As AcadEntity
    Dim splyObj As AcadLWPolyline
    Dim newObj As AcadLWPolyline
    
    
    Dim UsersSelection As AcadSelectionSet
    
    
    Dim DrawingSelected As AcadEntity 'delete the selection set if it already exists
    Dim intPoint12 As Variant
    Dim FilterType(0) As Integer
    Dim FilterData(0) As Variant
    Dim splyCoords() As Double
    
    Dim temp As Variant
    
    Dim index As Integer
    
    
    With ThisDrawing
        On Error Resume Next
        .SelectionSets("CurrentSelection").Delete
        'get selection from user
        MsgBox "Select objects! Hit Enter to finish!"
        Set UsersSelection = .SelectionSets.add("CurrentSelection")
        
        FilterType(0) = 0
        FilterData(0) = "LWPolyline"
        
        UsersSelection.SelectOnScreen FilterType, FilterData
        Set SelPl(0) = UsersSelection.Item(0)
        Set SelPl(1) = UsersSelection.Item(1)
        
        intPoint12 = SelPl(0).IntersectWith(SelPl(1), acExtendNone)
         
        
        splyCoords = SelPl(0).Coordinates
        splyCoords(7) = 2000
        
        SelPl(0).Update
        
        
        Set newObj = ThisDrawing.ModelSpace.AddLightWeightPolyline(splyCoords)
        newObj.Closed = True
        
         
        
        
    End With

End Sub

Attribute VB_Name = "Module4"
 





Function mergeAll(d1() As Double, d2() As Double, d3() As Double, d4() As Double) As Double()

    Dim dout() As Double
    Dim count As Integer
    Dim reverse As Boolean
    
    
    reverse = False
    
    'count = UBound(d1) + UBound(d2) + 3 - 2
    'count = UBound(d1) + UBound(d2) + UBound(d3) + 4 - 2
    count = UBound(d1) + UBound(d2) + UBound(d3) + UBound(d4) + 3 - 2
    
    ReDim dout(count) As Double
    
    idx = 0
    
    For i = 0 To UBound(d1)
        dout(idx) = d1(i)
        idx = idx + 1
    Next
    
    
    addDonut3 d1(0), d1(1)
    addDonut3 dout(idx - 2), dout(idx - 1)
    
    If d2(0) = d1(UBound(d1) - 1) Then
        reverse = False
    Else
        reverse = True
    End If
    
    If reverse = False Then
        For i = 2 To UBound(d2) Step 2
            dout(idx) = d2(i)
            idx = idx + 1
            dout(idx) = d2(i + 1)
            idx = idx + 1
            addDonut3 dout(idx - 2), dout(idx - 1)
        Next
        
    Else
        For i = UBound(d2) - 3 To 0 Step -2
            dout(idx) = d2(i)
            idx = idx + 1
            dout(idx) = d2(i + 1)
            idx = idx + 1
            addDonut3 dout(idx - 2), dout(idx - 1)
        Next
    End If
        
    If reverse = False Then
        For i = 2 To UBound(d3) Step 2
            dout(idx) = d3(i)
            idx = idx + 1
            dout(idx) = d3(i + 1)
            idx = idx + 1
            addDonut3 dout(idx - 2), dout(idx - 1)
     
        Next
    Else
        For i = UBound(d3) - 1 To 0 Step -2
            dout(idx) = d3(i)
            idx = idx + 1
            dout(idx) = d3(i + 1)
            idx = idx + 1
            addDonut3 dout(idx - 2), dout(idx - 1)
        Next
    End If
    
    If d3(0) = d2(UBound(d2) - 1) Then
        reverse = reverse
    Else
        reverse = Not reverse
    End If
    
    If reverse = True Then 'd3(0) = d2(UBound(d2) - 1)
        For i = 2 To UBound(d4) Step 2
            dout(idx) = d4(i)
            idx = idx + 1
            dout(idx) = d4(i + 1)
            idx = idx + 1
            addDonut3 dout(idx - 2), dout(idx - 1)
        Next
    Else
        For i = UBound(d4) - 1 To 0 Step -2
            dout(idx) = d4(i)
            idx = idx + 1
            dout(idx) = d4(i + 1)
            idx = idx + 1
            addDonut3 dout(idx - 2), dout(idx - 1)
        Next
    End If
    
     
    'addDonut3 d4(0), d4(1)
    'addDonut3 dout(idx - 2), dout(idx - 1)

    
    
    
    mergeAll = dout
    
    

End Function



Function searchInnerLine(plObj As AcadEntity, f1obj As AcadEntity, f2obj As AcadEntity) As Double()
    searchInnerLine = searchCrossLine(plObj, f1obj, f2obj, True)
End Function

Function searchOutLine(plObj As AcadEntity, f1obj As AcadEntity, f2obj As AcadEntity) As Double()

    searchOutLine = searchCrossLine(plObj, f1obj, f2obj, False)

End Function


Function searchCrossLine(plObj As AcadEntity, f1obj As AcadEntity, f2obj As AcadEntity, isinner As Boolean) As Double()

    Dim dpl() As Double
    Dim df1() As Double
    Dim df2() As Double
    Dim point As Double
    
    Dim f1idx, f1idxn As Integer    '필렛1 접점 인덱스
    Dim f2idx, f2idxn As Integer    '필렛2 접점 인덱스
    
    Dim index1, index1n As Integer   '폴리라인 접점 인덱스
    
    
    Dim dret() As Double    '리턴좌표
    Dim itotal As Integer
    
    'Set ret = Nothing
    
    dpl = plObj.Coordinates '폴리라인
    df1 = f1obj.Coordinates '필렛1
    df2 = f2obj.Coordinates '필렛2

    x = df1(0)
    y = df1(1)
    
    
    index1 = searchIndex(dpl, x, y)
    
    If index1 = -1 Then
        count = UBound(df1)
        
        x = df1(count - 1)
        y = df1(count)
        
        index1 = searchIndex(dpl, x, y)
        f1idx = count - 1
        f1idxn = count - 3
    Else
        f1idx = 0
        f1idxn = 2
        
    
    End If
    
    x = df2(0)
    y = df2(1)
    
    index2 = searchIndex(dpl, x, y)
    
    If index2 = -1 Then
        count = UBound(df2)
        
        x = df2(count - 1)
        y = df2(count)
        
        index2 = searchIndex(dpl, x, y)
        f2idx = count - 1
        f2idxn = count - 3
    Else
        f2idx = 0
        f2idxn = 2
    End If
    


    If index1 + 2 > UBound(dpl) Then
        index1n = index1 - 2
    Else
        index1n = index1 + 2
    End If


    cx = dpl(index1)
    cy = dpl(index1 + 1)
    
    x1 = dpl(index1n)
    y1 = dpl(index1n + 1)
    
    x2 = df1(f1idxn)
    y2 = df1(f1idxn + 1)

    'addDonut3 cx, cy
    'addDonut3 x1, y1
    'addDonut3 x2, y2
    


    rad = Abs(Atn((y2 - cy) / (x2 - cx)) - Atn((y1 - cy) / (c1 - cx)))
    
    
    
    If (rad < 1.571) = isinner Then '삭제영역에 해당함
    
        itotal = UBound(dpl)
        If index2 = 0 Then
            index2 = itotal
        End If
        
        If index2 > index1 Then     '올바른 방향임
            count = index2 - index1 + 2
            ReDim dret(0 To count) As Double
            
            idx = 0
            
            For i = index1 To index2 + 2 Step 2
            
                If i > itotal Then
                    dret(idx) = dpl(i - (itotal + 1))
                    idx = idx + 1
                    dret(idx) = dpl(i - (itotal + 1) + 1)
                    idx = idx + 1
                Else
                    dret(idx) = dpl(i)
                    idx = idx + 1
                    dret(idx) = dpl(i + 1)
                    idx = idx + 1
                End If
            
                'addDonut3 dret(idx - 2), dret(idx - 1)
            Next
        
        Else
            count = index1 - index2 + 1
            ReDim dret(0 To count) As Double
            
            idx = 0
            
            For i = index2 To index1 + 1 Step 2
                dret(idx) = dpl(i)
                idx = idx + 1
                dret(idx) = dpl(i + 1)
                idx = idx + 1
            Next
            'count = index1 - index2 + 1
            'ReDim dret(0 To count) As Double
            
            'idx = 0
            'For i = index1 To index2 Step -2
            '   dret(idx) = dpl(i)
            '   idx = idx + 1
            '   dret(idx) = dpl(i + 1)
            '   idx = idx + 1
            '   addDonut3 dpl(i), dpl(i + 1)
            
            'Next
            
        
        End If
        
    Else
        If index2 > index1 Then
        
            count = index1 + UBound(dpl) - index2 + 2   'y좌표 2개라서 +2
            ReDim dret(0 To count) As Double
            idx = 0
        
            For i = index2 To UBound(dpl)   '개수만큼 찾기때문에 y가 포함됨 +1 안함
                dret(idx) = dpl(i)
                idx = idx + 1
            Next
                    
            For i = 0 To index1 + 1 'y좌표 포함해야하므로 +1
                dret(idx) = dpl(i)
                idx = idx + 1
            Next
             
            
            
            
        Else
        
        End If
    
    End If
    
    
    
    searchCrossLine = dret
    

End Function

Function searchIndex(d() As Double, ByVal x As Double, ByVal y As Double) As Integer

    Dim index As Integer
    
    index = -1
    
    For i = 0 To UBound(d) Step 2
    
        If d(i) = x And d(i + 1) = y Then
            index = i
        End If
    
    Next


    searchIndex = index
    
End Function


 

 

Sub SelectRawData()
    Dim i, ii, x, y As Integer
    Dim FilterType(0) As Integer
    Dim FilterData(0) As Variant
    Dim UsersSelection As AcadSelectionSet
    Dim selObj() As AcadEntity
    Dim ret As Integer
    Dim arcObjs() As AcadEntity
    Dim ddd() As Double
    Dim x2, y2 As Variant
    Dim count As Integer
    Dim newv(0 To 1) As Double
    
    
    With ThisDrawing
        On Error Resume Next
        .SelectionSets("CurrentSelection").Delete
        Set UsersSelection = .SelectionSets.add("CurrentSelection")
        
        
        FilterType(0) = 0
        FilterData(0) = "LWPolyline"
        
        UsersSelection.SelectOnScreen FilterType, FilterData
        
        
        count = getEntitySize(UsersSelection, "AcDbPolyline") - 1 'AcDbArc
        
        ReDim selObj(0 To count) As AcadEntity
        
        For i = 0 To count
            Set selObj(i) = UsersSelection.Item(i)
             
        Next i
        
        
    End With
    
    
    vx = 1194.35534891423
    vy = 2999.85414787302
    newv(0) = vx: newv(1) = vy
    
    For i = 0 To count
        ddd = selObj(i).Coordinates
        count = UBound(ddd)
        
        x1 = ddd(count - 1)
        y1 = ddd(count)
        
        For ii = 0 To count Step 2
        
            x2 = ddd(ii)
            y2 = ddd(ii + 1)
            
            f = (y2 - y1) / (x2 - x1)
            
            f1 = (vy - y1) / (vx - x1)
            f2 = (y2 - vy) / (x2 - vx)
            
            If Abs(f1 - f2) < 0.00001 Then
                addDonut x2, y2
                addDonut x1, y1
                
                selObj(i).addVertex ii / 2, newv
                selObj(i).Update
            
            End If
            
            x1 = x2
            y1 = y2
            
        Next ii
    Next i
     
    
    
End Sub
 
  

Sub test()
    
    Dim SelPl(0 To 1) As AcadEntity
    Dim splyObj As AcadLWPolyline
    Dim newObj As AcadLWPolyline
    
    
    Dim UsersSelection As AcadSelectionSet
    
    
    Dim DrawingSelected As AcadEntity 'delete the selection set if it already exists
    Dim intPoint12 As Variant
    Dim FilterType(0) As Integer
    Dim FilterData(0) As Variant
    Dim splyCoords() As Double
    
    Dim temp As Variant
    
    Dim index As Integer
    
    
    With ThisDrawing
        On Error Resume Next
        .SelectionSets("CurrentSelection").Delete
        'get selection from user
        MsgBox "Select objects! Hit Enter to finish!"
        Set UsersSelection = .SelectionSets.add("CurrentSelection")
        
        FilterType(0) = 0
        FilterData(0) = "LWPolyline"
        
        UsersSelection.SelectOnScreen FilterType, FilterData
        Set SelPl(0) = UsersSelection.Item(0)
        Set SelPl(1) = UsersSelection.Item(1)
        
        intPoint12 = SelPl(0).IntersectWith(SelPl(1), acExtendNone)
         
        
        splyCoords = SelPl(0).Coordinates
        splyCoords(7) = 2000
        
        SelPl(0).Update
        
        
        Set newObj = ThisDrawing.ModelSpace.AddLightWeightPolyline(splyCoords)
        newObj.Closed = True
         
        
        
    End With

End Sub

Attribute VB_Name = "MyMath"
Function getLinearEQuationA(ByVal x1 As Double, ByVal y1 As Double, ByVal x2 As Double, ByVal y2 As Double) As Double
    Dim dx As Double
    Dim ret As Double
    dx = x2 - x1
    If dx = 0 Then
        dx = 1
    End If
    
    ret = (y2 - y1) / dx
    
    getLinearEQuationA = ret

End Function

Function getLinearEQuationC(ByVal x1 As Double, ByVal y1 As Double, ByVal x2 As Double, ByVal y2 As Double) As Double

    getLinearEQuationC = -getLinearEQuationA(x1, y1, x2, y2) * x1 + y1

End Function


Function getShortestDistance(ByVal x1 As Double, ByVal y1 As Double, ByVal x2 As Double, ByVal y2 As Double, ByVal x As Double, ByVal y As Double) As Double

    Dim a, b, c, d As Double

    a = getLinearEQuationA(x1, y1, x2, y2)
    b = -1
    c = getLinearEQuationC(x1, y1, x2, y2)
    
    d = Abs((a * x + b * y + c)) / Sqr(a * a + b * b)
     
    getShortestDistance = d


End Function


Function getDistance(ByVal x1 As Double, ByVal y1 As Double, ByVal x2 As Double, ByVal y2 As Double) As Double

    getDistance = Sqr((x2 - x1) * (x2 - x1) + (y2 - y1) * (y2 - y1))

End Function



Function getAngleEx(ByVal cx As Double, ByVal cy As Double, ByVal x1 As Double, ByVal y1 As Double, ByVal x2 As Double, ByVal y2 As Double) As Double

    getAngleEx = ArcTan2((x2 - cx), (y2 - cy)) - ArcTan2((x1 - cx), (y1 - cy))
    
End Function


Function getAngle(ByVal x1 As Double, ByVal y1 As Double, ByVal x2 As Double, ByVal y2 As Double) As Double

    Dim dx, dy, rad As Double

    dx = x2 - x1
    dy = y2 - y1

    
    rad = ArcTan2(dx, dy)
    
    getAngle = rad
    
End Function

Function crossXY(ByVal cx As Double, ByVal cy As Double, ByVal x1 As Double, ByVal y1 As Double, ByVal x2 As Double, ByVal y2 As Double) As Double()

    Dim d, r As Double
    Dim th, rad, radex As Double
    Dim nx, ny As Double
    Dim dx, dy As Double
    Dim ret(0 To 2) As Double
    
 
    d = getShortestDistance(x1, y1, x2, y2, cx, cy)
    
    rad = getAngle(x1, y1, x2, y2)
    
    rad = Abs(rad)
    
    If rad > 0 And rad > PI_2 Then
        rad = PI - rad
    End If
    
    If rad < 0 And rad < -PI_2 Then
        rad = PI + rad
    End If
    
    
    
    radex = getAngleEx(x1, y1, cx, cy, x2, y2)
    
    radex = Abs(radex)
    
    r = getDistance(x1, y1, cx, cy)
    
    
    'r = d / Tan(radex)
    dx = r * Cos(rad)
    dy = r * Sin(rad)

    If x2 > x1 Then
        nx = x1 + dx
    Else
        nx = x1 - dx
    End If
    
    
    If y2 > y1 Then
        ny = y1 + dy
    Else
        ny = y1 - dy
    End If
    

    'addDonut2 cx, cy
    'addDonut2 x1, y1
    'addDonut2 x2, y2
    'addDonut2 nx, ny
    
    
    ret(0) = nx
    ret(1) = ny
    
    crossXY = ret
    

End Function



Function isEqualsDouble(x1 As Double, y1 As Double, x2 As Double, y2 As Double) As Boolean

    Dim b, b1, b2 As Boolean
    Dim xx1, yy1, xx2, yy2 As Long
    xx1 = CLng(x1 * 1000)
    yy1 = CLng(y1 * 1000)
    xx2 = CLng(x2 * 1000)
    yy2 = CLng(y2 * 1000)
    
    b1 = (xx1 = xx2)
    b2 = (yy1 = yy2)
    
    isEqualsDouble = (b1 And b2)


End Function
 

Function DegreesToRadians(sngDegree As Double) As Double
    DegreesToRadians = sngDegree * PI / 180
End Function

Function RadiansToDegrees(sngRads As Single) As Double
    RadiansToDegrees = sngRads * 180 / PI
End Function

Attribute VB_Name = "Test"


Sub SelectRawData()
    Dim i, ii, x, y As Integer
    Dim FilterType(0) As Integer
    Dim FilterData(0) As Variant
    Dim UsersSelection As AcadSelectionSet
    Dim selObj() As AcadEntity
    Dim ret As Integer
    Dim arcObjs() As AcadEntity
    Dim ddd() As Double
    Dim x2, y2 As Variant
    Dim count As Integer
    Dim newv(0 To 1) As Double
    
    
    With ThisDrawing
        On Error Resume Next
        .SelectionSets("CurrentSelection").Delete
        Set UsersSelection = .SelectionSets.add("CurrentSelection")
        
        
        FilterType(0) = 0
        FilterData(0) = "LWPolyline"
        
        UsersSelection.SelectOnScreen FilterType, FilterData
        
        
        count = getEntitySize(UsersSelection, "AcDbPolyline") - 1 'AcDbArc
        
        ReDim selObj(0 To count) As AcadEntity
        
        For i = 0 To count
            Set selObj(i) = UsersSelection.Item(i)
             
        Next i
        
        
    End With
    
    
    vx = 1194.35534891423
    vy = 2999.85414787302
    newv(0) = vx: newv(1) = vy
    
    For i = 0 To count
        ddd = selObj(i).Coordinates
        count = UBound(ddd)
        
        x1 = ddd(count - 1)
        y1 = ddd(count)
        
        For ii = 0 To count Step 2
        
            x2 = ddd(ii)
            y2 = ddd(ii + 1)
            
            f = (y2 - y1) / (x2 - x1)
            
            f1 = (vy - y1) / (vx - x1)
            f2 = (y2 - vy) / (x2 - vx)
            
            If Abs(f1 - f2) < 0.00001 Then
                addDonut x2, y2
                addDonut x1, y1
                
                selObj(i).addVertex ii / 2, newv
                selObj(i).Update
            
            End If
            
            x1 = x2
            y1 = y2
            
        Next ii
    Next i
     
    
    
End Sub


Sub test_mkdir()

    Debug.Print getShpExportPropFile
   
End Sub





Sub test_command()

    Dim cmd As String
    Dim str As String
    
    
    dr = "SHPEXPORT_" & Format(Now, "yyyyMMdd_hhmmss")

    Debug.Print dr

    MkDir dr
    
    'cmd = "-mapexport" & vbCr & "SHP" & vbCr & "MyTest.shp" & vbCr & "Y" & vbCr & "danji_a.epf" & vbCr & "S" & vbCr & "L" & vbCr & "All" & vbCr & "*" & vbCr & "*" & vbCr & "No" & vbCr & "Proceed"

    'cmd = "(command ""-mapexport"" ""SHP"" ""MyTest2.shp"" ""Y"" ""danji_a.epf"" ""S"" ""L"" ""All"" ""*"" ""*"" ""No"" ""Proceed"") & vbCr"

    cmd = "(command ""-mapexport"" ""SHP"" """ & dr & "\\도로_수도.shp"" ""Y"" ""도로_수도.epf"" ""Proceed"" )" & vbLf
    
    ThisDrawing.SendCommand cmd
    
    
    
 
    
    
    'cmd = " ""-mapexport"" ""SHP"" ""MyTest12.shp"" ""Y"" ""danji_a.epf"" ""Proceed"" & vbCr"
    



    'ThisDrawing.SendCommand "-mapexport" & vbCr & "SHP" & vbCr & "MyTest13.shp" & vbCr & "Y" & vbCr & "danji_a.epf" & vbCr & "Proceed" & vbCr
    
    

End Sub

Sub test_lyr()
    Dim dict As Dictionary
    Dim size As Integer
    Dim key As Variant
    Dim value As Variant
    
    Set dict = getBaseLayer
    
    For Each key In dict
    
        value = dict.Item(key)
        Debug.Print key & "> " & value
        
    Next
    
    
    
    
End Sub

Attribute VB_Name = "Test2"
Private Const PI As Double = 3.14159265358979
Private Const PI_2 As Double = 1.5707963267949


Sub Createcircle2()
    Dim i, ii, x, y As Integer
    Dim FilterType(0) As Integer
    Dim FilterData(0) As Variant
    Dim UsersSelection As AcadSelectionSet
    Dim selObj() As AcadEntity
    Dim ret As Integer
    Dim arcObjs() As AcadEntity
    Dim ddd() As Double
    Dim x2, y2 As Variant
    Dim count As Integer
    Dim newv(0 To 1) As Double
    Dim centerPoint(0 To 2) As Double
    
    Dim returnObj1 As AcadObject
    Dim returnObj3 As AcadObject
    
    Dim retArc As AcadArc
    
    Dim p1(0 To 2) As Double
    Dim p2() As Double
    Dim p3(0 To 2) As Double
    
    Dim retLine As AcadEntity
    Dim dout1() As Double
    Dim dout2() As Double
    Dim nnnn As Variant
    Dim newp1() As Double
    Dim newp2() As Double
    
    With ThisDrawing
        On Error Resume Next
        .SelectionSets("CurrentSelection").Delete
        Set UsersSelection = .SelectionSets.add("CurrentSelection")

        
        ThisDrawing.SetVariable "osmode", 512
        ThisDrawing.Utility.getEntity returnObj1, tmp, "Enter a point 1: "
            
        p1(0) = tmp(0)
        p1(1) = tmp(1)
            
        ThisDrawing.SetVariable "osmode", 0
        p2 = ThisDrawing.Utility.getPoint(, "Enter a point2: ")
         
        ThisDrawing.SetVariable "osmode", 512
        ThisDrawing.Utility.getEntity returnObj3, tmp, "Enter a point 3: "
        
        p3(0) = tmp(0)
        p3(1) = tmp(1)
        
        
        Set retArc = getArcBy3P(p1, p2, p3) '세점을 지나는 아크를 생성
        
        
        Set retLine = arc2line(retArc)  '아크를 라인으로 변경
        retArc.Delete
        retArc.Update
        retLine.Update
         
         
    End With
    
    
    nnnn = addCrossVertext(returnObj1, returnObj3)  '도로의 접점 추가
    
   
    newp1 = findVertex(returnObj1, retLine)   '아크와 도로(새도로)의 접점 추가
    newp2 = findVertex(returnObj3, retLine)   '아크와 도로(구도로)의 접점 추가
   
    
   
    'dout1 = searchOutLine(plroad(0), plObjs(0), plObjs(1))
    
    'ThisDrawing.ModelSpace.AddLightWeightPolyline(dout1).color = acRed
    
    'dout2 = searchInnerLine(plroad(1), plObjs(0), plObjs(1))
    
End Sub



Function searchInnerLine1(plObj As AcadEntity, f1obj As AcadEntity) As Double()
    searchInnerLine = searchCrossLine1(plObj, f1obj, True)
End Function

Function searchOutLine1(plObj As AcadEntity, f1obj As AcadEntity) As Double()

    searchOutLine = searchCrossLine1(plObj, f1obj, False)

End Function


Function searchCrossLine1(plObj As AcadEntity, f1obj As AcadEntity, isinner As Boolean) As Double()

    Dim dpl() As Double
    Dim df1() As Double
    Dim point As Double
    
    Dim f1idx, f1idxn As Integer    '필렛1 접점 인덱스
    
    Dim index1, index1n As Integer   '폴리라인 접점 인덱스
    
    
    Dim dret() As Double    '리턴좌표
    Dim itotal As Integer
    
    'Set ret = Nothing
    
    dpl = plObj.Coordinates '폴리라인
    df1 = f1obj.Coordinates '필렛1
    

    x = df1(0)
    y = df1(1)
    
    
    index1 = searchIndex(dpl, x, y)
    
    If index1 = -1 Then
        count = UBound(df1)
        
        x = df1(count - 1)
        y = df1(count)
        
        index1 = searchIndex(dpl, x, y)
        f1idx = count - 1
        f1idxn = count - 3
    Else
        f1idx = 0
        f1idxn = 2
        
    
    End If
    
    

    If index1 + 2 > UBound(dpl) Then
        index1n = index1 - 2
    Else
        index1n = index1 + 2
    End If


    cx = dpl(index1)
    cy = dpl(index1 + 1)
    
    x1 = dpl(index1n)
    y1 = dpl(index1n + 1)
    
    x2 = df1(f1idxn)
    y2 = df1(f1idxn + 1)

    'addDonut3 cx, cy
    'addDonut3 x1, y1
    'addDonut3 x2, y2
    


    rad = Abs(Atn((y2 - cy) / (x2 - cx)) - Atn((y1 - cy) / (c1 - cx)))
    
    
    
    If (rad < 1.571) = isinner Then '삭제영역에 해당함
    
        itotal = UBound(dpl)
        If index2 = 0 Then
            index2 = itotal
        End If
        
        If index2 > index1 Then     '올바른 방향임
            count = index2 - index1 + 2
            ReDim dret(0 To count) As Double
            
            idx = 0
            
            For i = index1 To index2 + 2 Step 2
            
                If i > itotal Then
                    dret(idx) = dpl(i - (itotal + 1))
                    idx = idx + 1
                    dret(idx) = dpl(i - (itotal + 1) + 1)
                    idx = idx + 1
                Else
                    dret(idx) = dpl(i)
                    idx = idx + 1
                    dret(idx) = dpl(i + 1)
                    idx = idx + 1
                End If
            
                'addDonut3 dret(idx - 2), dret(idx - 1)
            Next
        
        Else
            count = index1 - index2 + 1
            ReDim dret(0 To count) As Double
            
            idx = 0
            
            For i = index2 To index1 + 1 Step 2
                dret(idx) = dpl(i)
                idx = idx + 1
                dret(idx) = dpl(i + 1)
                idx = idx + 1
            Next
            'count = index1 - index2 + 1
            'ReDim dret(0 To count) As Double
            
            'idx = 0
            'For i = index1 To index2 Step -2
            '   dret(idx) = dpl(i)
            '   idx = idx + 1
            '   dret(idx) = dpl(i + 1)
            '   idx = idx + 1
            '   addDonut3 dpl(i), dpl(i + 1)
            
            'Next
         
            
        
        End If
        
    Else
        If index2 > index1 Then
        
            count = index1 + UBound(dpl) - index2 + 2   'y좌표 2개라서 +2
            ReDim dret(0 To count) As Double
            idx = 0
        
            For i = index2 To UBound(dpl)   '개수만큼 찾기때문에 y가 포함됨 +1 안함
                dret(idx) = dpl(i)
                idx = idx + 1
            Next
                    
            For i = 0 To index1 + 1 'y좌표 포함해야하므로 +1
                dret(idx) = dpl(i)
                idx = idx + 1
            Next
             
            
            
            
        Else
        
        End If
    
    End If
    
    
    
    searchCrossLine = dret
    

End Function

Function searchIndex(d() As Double, ByVal x As Double, ByVal y As Double) As Integer

    Dim index As Integer
    
    index = -1
    
    For i = 0 To UBound(d) Step 2
    
        If d(i) = x And d(i + 1) = y Then
            index = i
        End If
    
    Next


    searchIndex = index
    
End Function

Attribute VB_Name = "Test3"
Sub test600()

    Dim dict As New Dictionary
    
    dict.add 0", 1
    

End Sub

Sub test4()

    Dim plroad() As AcadEntity
    Dim ret As Variant
    
    plroad = selectPolylineObs  'select two polylines(one is a source, the ohter is a target entity.
     
    
    ret = addCrossVertext(plroad(0), plroad(1))
    
    
    Set temp = ThisDrawing.ActiveLayer
    Set pp = plroad(0)
    
    Debug.Print "ActiveLayer: " & temp.name
    pp.layer = temp.name
    
    
    

End Sub


Sub test77()

    Dim selec As New ClsSelEntity
    Dim ent As AcadEntity
    Dim pt As New clsPoint
    
    selec.selectPolyline ("Get Polyline 1: ")
    Set ent = selec.getEntity
    Set pt = selec.getPoint
        
    Debug.Print ""
    

End Sub


Sub test78()

    Dim seler As New ClsSelReal
    Dim rad As Double
    Dim test As Variant
    
    rad = seler.selectReal
    
    Debug.Print " "

End Sub

Sub test79()


    Dim seles As New clsSelSets
    Dim ent As AcadEntity
    
    Set ent = seles.selectArc
    

End Sub
 
 
Sub test80()

    newLayer "TEST"

End Sub

Sub test501()

    Dim ent As AcadEntity
    Set ent = selectEntity
    
    
    If TypeOf ent Is AcadCircle Then
        cir2line ent
    ElseIf TypeOf ent Is AcadArc Then
        arc2line ent
    End If
    
    ent.Delete
    
End Sub


 
Sub testSelection()

    Dim newroad As AcadEntity
    Dim basePnt1 As Variant
        
    On Error GoTo errControl
    
start:
    ThisDrawing.Utility.getEntity newroad, basePnt1, "Get Object1: "
    
    
errControl:
    
    If Err.Description = "Method 'GetEntity' of object 'IAcadUtility' failed" Then
    
        If CheckKey(VK_ESCAPE) = True Then
            Debug.Print "End"
        
            End
        Else
            Debug.Print "Resume"
            Resume
        End If
    Else
        MsgBox Err.Description
    End If
    

End Sub

Sub test56()
    Dim plroad() As AcadEntity
    Dim ret As Variant
    Dim rad As Double
    
    Dim newroad As AcadObject
    Dim basePnt1 As Variant
    
    Dim oldroad As AcadObject
    Dim basePnt2 As Variant
    
    Dim pt1 As New clsPoint
    Dim pt2 As New clsPoint
    
    
    Dim pr1 As New clsPolygonReader
    Dim pr2 As New clsPolygonReader
    
    Dim line1 As AcadLine
    Dim line2 As AcadLine
    Dim np3 As New clsPoint
    Dim result As AcadLine
    
    Dim retArc As AcadEntity
 
    ThisDrawing.Utility.getEntity newroad, basePnt1, "Get Object1: "
    'ret = addCrossVertext(plroad(0), plroad(1))
    
    ThisDrawing.Utility.getEntity oldroad, basePnt2, "Get Object2: "
    'ret = addCrossVertext(plroad(0), plroad(1))
    
    ptIntersection = searchCrossVertext(newroad, oldroad)
    
    pt1.x = basePnt1(0)
    pt1.y = basePnt1(1)
    
    pt2.x = basePnt2(0)
    pt2.y = basePnt2(1)
    
    
    Set np3 = getNearPoint2(ptIntersection, pt2)
    
    'addDonut5 np3.x, np3.y
    
    pr1.init newroad
    Set line1 = pr1.getLine(pt1)
    
    pr2.init oldroad
    Set line2 = pr2.getLine(pt2)
    
    Set result = getShortestLine(line2, pt2, np3)
    
    
    
    'line1.Handle
    'line2.Handle
    
    'Application.ActiveDocument.SendCommand "_chamfer" & vbCr & "D" & vbCr & "1" & vbCr & "1" & vbCr & "(HandEnt """ & line1.Handle & """)" & vbCr & "(HandEnt """ & line2.Handle & """)" & vbCr
    Application.ActiveDocument.SendCommand "_fillet" & vbCr & "T" & vbCr & "N" & vbCr & "r" & vbCr & "3" & vbCr & "(HandEnt """ & line1.Handle & """)" & vbCr & "(HandEnt """ & result.Handle & """)" & vbCr
    
    
    If line2.Handle <> result.Handle Then
        result.Delete
    End If
    
    line1.Delete
    line2.Delete
    
    Dim ssetObj As AcadSelectionSet
    Set ssetObj = ThisDrawing.ActiveSelectionSet
    
    
    
    ssetObj.Select acSelectionSetLast
    
     For Each ent In ssetObj
        Set retArc = ent
     Next
    
    
    
    
    
    
    Debug.Print " "


End Sub


Function getShortestLine(line As AcadLine, ct As clsPoint, pt As clsPoint) As AcadLine

    Dim newline As AcadLine
    
    Dim sp() As Double
    Dim ep() As Double
        
    L12 = line.length
    
    sp = line.startPoint
    ep = line.endPoint
    
    L13 = getDistance(sp(0), sp(1), pt.x, pt.y)
    L23 = getDistance(ep(0), ep(1), pt.x, pt.y)
    
    L1C = getDistance(sp(0), sp(1), ct.x, ct.y)
    L2C = getDistance(ep(0), ep(1), ct.x, ct.y)
    
    
    If L12 > L13 And L12 > L23 Then
        
        If L1C < L13 Then
            'L13
            sp(0) = sp(0)
            sp(1) = sp(1)
            ep(0) = pt.x
            ep(1) = pt.y
            
        Else        ' L1C < L23
            'L23
            sp(0) = ep(0)
            sp(1) = ep(1)
            ep(0) = pt.x
            ep(1) = pt.y
            
        End If
        
        Set newline = ThisDrawing.ModelSpace.addLine(sp, ep)
        
        'line.Delete
    ElseIf L12 > L23 And L12 > L13 Then
        
       'L13
        sp(0) = sp(0)
        sp(1) = sp(1)
        ep(0) = pt.x
        ep(1) = pt.y
        
        Set newline = ThisDrawing.ModelSpace.addLine(sp, ep)
        'line.Delete
   
    Else
    
        Set newline = line
    
    End If
    
    
    Debug.Print ""
    
    Set getShortestLine = newline


End Function


Sub test55()

    Dim plroad() As AcadEntity
    Dim ret As Variant
    Dim rad As Double
    
    plroad = selectObjs 'select two polylines(one is a source, the ohter is a target entity.
     
    
    'ret = addCrossVertext(plroad(0), plroad(1))
    
    
    
    
    
    
    Set tmp1 = plroad(0)
    Set tmp2 = plroad(1)
    
    
    tmp3 = tmp1.Handle
    tmp4 = tmp2.Handle
    
    Application.ActiveDocument.SendCommand "_chamfer" & vbCr & "D" & vbCr & "1" & vbCr & "1" & vbCr & "(HandEnt """ & tmp1.Handle & """)" & vbCr & "(HandEnt """ & tmp2.Handle & """)" & vbCr
    'Application.ActiveDocument.SendCommand "_fillet" & vbCr & "T" & vbCr & "N" & vbCr & "r" & vbCr & "3" & vbCr & "(HandEnt """ & tmp1.Handle & """)" & vbCr & "(HandEnt """ & tmp2.Handle & """)" & vbCr
    
    
    
    
    Debug.Print " "
    

End Sub


Sub LineFillet()



ThisDrawing.SendCommand "_fillet" & vbCr & "T" & vbCr & "N" & vbCr & "r" & vbCr & "3" & vbCr
ThisDrawing.SendCommand "(HandEnt """ & r.Handle & """)" & vbCr
ThisDrawing.SendCommand "(HandEnt """ & plineObj.Handle & """)" & vbCr


Debug.Print "done"
   'ThisDrawing.SendCommand "fillet T N r 3"
   'ThisDrawing.ModelSpace.ad
           
End Sub

 
Public Sub testFillet()

    Dim doc As Document

    doc = Application.DocumentManager.MdiActiveDocument

    Dim ed As Editor
    ed = doc.Editor

    Dim Db As Database
    Db = doc.Database



    Dim pEntRes1 As PromptEntityResult
    pEntRes1 = ed.getEntity("Select first line to Fillet")

    If pEntRes1.Status <> PromptStatus.ok Then

        Return

    End If



    Dim obj1 As String
    obj1 = pEntRes1.ObjectID.ObjectClass.name



    Dim pEntRes2 As PromptEntityResult
    pEntRes2 = ed.getEntity("Select second line to Fillet")

    If pEntRes2.Status <> PromptStatus.ok Then

        Return

    End If



    obj1 = pEntRes2.ObjectID.ObjectClass.name


    Dim strHandle1 As String
    
    strHandle1 = pEntRes1.ObjectID.Handle.ToString()

    Dim strEntName1 As String
    strEntName1 = "(handent """ & strHandle1 & """)"



    Dim strHandle2 As String
    strHandle2 = pEntRes2.ObjectID.Handle.ToString()

    Dim strEntName2 As String
    strEntName2 = "(handent """ & strHandle2 & """)"

    Dim strCommand As String
    strCommand = "_fillet" + vbCr + "r" + vbCr + "0.495" + vbCr + strEntName1 + vbCr + strEntName2 + vbCr

    doc.AcadDocument.SendCommand (strCommand)



End Sub

Public Sub prob2()
    Dim ssetObj As AcadSelectionSet
    Set ssetObj = ThisDrawing.PickfirstSelectionSet
    ssetObj.Clear
    
    ' asks for an entity and put it into the sset
    Dim returnObj As AcadObject
    Dim basePnt As Variant
    ThisDrawing.Utility.getEntity returnObj, basePnt, "Select object: "
    Dim objlist(0) As AcadObject
    Set objlist(0) = returnObj
    ' difference from previous version
    Dim objlistvar As Variant
    objlistvar = objlist
    ssetObj.AddItems objlistvar
    ' then delete the sset to make it the "previous selection set"
    ssetObj.Delete
    
    Set ssetObj = ThisDrawing.PickfirstSelectionSet ' or whatever ss
    ssetObj.Select acSelectionSetPrevious
End Sub



Public Sub FilletVertex(ByVal LWPline As AcadLWPolyline, _
    ByVal VertexNumber As Integer, ByVal Radius As Double, _
    Optional AsChamfer As Boolean)

    On Error Resume Next: DoEvents
    
    Dim IsConcave As Boolean
    Dim AngleToVertex As Double
    Dim AngleFromVertex As Double
    Dim AngleIncluded As Double
    Dim ptList As Variant
    Dim LastVertex As Integer
    Dim PrevVertex As Integer
    Dim NextVertex As Integer
    Dim Bulge As Double
    Dim pt1 As Variant
    Dim pt2 As Variant
    Dim pt2a As Variant
    Dim pt2b As Variant
    Dim pt3 As Variant
    Dim VertexA(1) As Double
    Dim VertexB(1) As Double
    Dim chamfer As Double
    Dim Util As AcadUtility
    
    Set Util = ThisDrawing.Utility

    If Radius = 0 Then
        Exit Sub
    ElseIf Radius < 0 Then
        Radius = Abs(Radius)
        IsConcave = True
    End If
    
    With LWPline
        ptList = .Coordinates
        
        LastVertex = (UBound(ptList) - 1) / 2
        If VertexNumber > LastVertex Then VertexNumber = 0
        NextVertex = VertexNumber + 1
        PrevVertex = VertexNumber - 1
        If NextVertex > LastVertex Then NextVertex = 0
        If PrevVertex < 0 Then PrevVertex = LastVertex
        
        If NextVertex = PrevVertex Then Exit Sub
        
        pt1 = .Coordinate(PrevVertex)
        pt2 = .Coordinate(VertexNumber)
        pt3 = .Coordinate(NextVertex)
    
        ReDim Preserve pt1(2): pt1(2) = 0
        ReDim Preserve pt2(2): pt2(2) = 0
        ReDim Preserve pt3(2): pt3(2) = 0
        
        AngleToVertex = Util.AngleFromXAxis(pt2, pt1)
        AngleFromVertex = Util.AngleFromXAxis(pt2, pt3)
        
        AngleIncluded = (AngleToVertex - AngleFromVertex)
        If AngleIncluded > PI Then
            AngleIncluded = AngleIncluded - (2 * PI)
        ElseIf AngleIncluded < -PI Then
            AngleIncluded = AngleIncluded + (2 * PI)
        End If
        

            
        If IsConcave Then
            chamfer = Radius
        Else
            chamfer = Radius * _
                Tan((PI - (Abs(AngleIncluded))) / 2)
        End If
        
        pt2b = Util.PolarPoint(pt2, _
            AngleFromVertex, chamfer)
        VertexB(0) = pt2b(0): VertexB(1) = pt2b(1)
        .Coordinate(VertexNumber) = VertexB
        
        pt2a = Util.PolarPoint(pt2, _
            AngleToVertex, chamfer)
        VertexA(0) = pt2a(0): VertexA(1) = pt2a(1)
        .addVertex VertexNumber, VertexA
        
        If Not AsChamfer Then

            If IsConcave Then
                Bulge = Tan((AngleIncluded) / -4#)
            Else
                Bulge = Tan((IIf(AngleIncluded > 0, PI, -PI) - AngleIncluded) / 4#)
            End If
            
             .SetBulge VertexNumber, Bulge

         End If
    End With
End Sub


Sub simplifyObject()    ' 오류

    Dim Userselection As AcadSelectionSet

    ThisDrawing.SelectionSets("CurrentSelection").Delete
    Set UsersSelection = ThisDrawing.SelectionSets.add("CurrentSelection")
        
    UsersSelection.SelectOnScreen
         
    
    
    tmp3 = UsersSelection.Handle

    ThisDrawing.SendCommand "(setq clean_id (tpm_cleanalloc))"
    ThisDrawing.SendCommand "(setq clean_var_id (tpm_varalloc))"
    ThisDrawing.SendCommand "(setq action_var_id (tpm_varalloc))"
    
    ThisDrawing.SendCommand "(tpm_varset clean_var_id ""CLEAN_TOL"" 2)"
    ThisDrawing.SendCommand "(tpm_varset clean_var_id ""INCLUDEOBJS_AUTOSELECT"" 0)"
    
    ThisDrawing.SendCommand "(tpm_cleanactionlistins clean_var_id 0 128 clean_var_id)"
    ThisDrawing.SendCommand "(setq DrwCleanresult (tpm_cleaninit clean_id clean_var_id (HandEnt """ & tmp1.Handle & """)))"
    ThisDrawing.SendCommand "(setq DrwCleanresult (tpm_cleanstart clean_id))"
    ThisDrawing.SendCommand "(tpm_cleanend clean_id)"
    
   

End Sub



Sub test100()

    ThisDrawing.StartUndoMark
    
    
    
    


End Sub



Sub test101()

    ThisDrawing.EndUndoMark
    
    
    ThisDrawing.SendCommand "Undo" & vbCr & "Back" & vbCr & "Y" & vbCr
    
    


End Sub


    
Sub test102()

    Dim plroad() As AcadEntity
    Dim ent As AcadEntity
    plroad = selectObjs
    
    
    For i = 0 To Bound(plroad)
        ent = plorad(i)
        showLayer ent.layer
    Next


End Sub

  
Sub test103()

    Dim plroad() As AcadEntity
    Dim ent As AcadEntity
    plroad = selectObjs
    
    
    For i = 0 To Bound(plroad)
        ent = plorad(i)
        hideLayer ent.layer
    Next


End Sub

Sub test104()

    Dim tmpfillet As AcadLWPolyline
    Dim tmpoldroad As AcadLWPolyline
    Dim intersec As Variant
    
    
    Dim plroad() As AcadEntity
    Dim ent As AcadEntity
    plroad = selectObjs
    
    intersec = searchCrossVertext(plroad(0), plroad(1))
    
    For i = 0 To UBound(intersec) Step 3
    
        addDonutA intersec(i), intersec(i + 1)
    Next
    
    
    
    Debug.Print ""
    

End Sub


Sub test105()

    Dim plroad As AcadEntity
    Dim ent As AcadEntity
    Dim ret As AcadEntity
    
    Dim ddd() As Double
    Set plroad = selectEntity

    Debug.Print ""
    
    
    Set ret = trimPolyline(plroad)
    
    plroad.Delete
    
    'ddd = ret.Coordinates
    '
    'For i = 0 To UBound(ddd) Step 2
    '    addDonutA ddd(i), ddd(i + 1)
    'Next
    
    
    '1146072.1709
End Sub


Public Sub test106()
    Dim Region As Variant
    Dim Objeto(0) As AcadEntity
    Dim selEntidad As AcadEntity
    Dim Solido As Acad3DSolid
    Dim Punto As Variant
    Dim Punto2 As Variant
    Dim Altura As Double
    Dim Angulo As Double
    
    Dim ent1 As AcadEntity
    Dim ent2 As AcadEntity
    
    Dim reg1 As AcadRegion
    Dim reg2 As AcadRegion
    Dim reg3 As AcadRegion
    
    Dim intent As AcadEntity
    Dim intent2 As AcadLWPolyline
    
    Dim temp As AcadRegion
    Dim temp2 As AcadRegion
    Dim ttt As Variant
    
    Dim regs() As AcadRegion
    
    Dim conv As New ClsConverter
    
    
    Dim ents() As AcadEntity
    Dim hasRegion As Boolean
    
    Altura = 10
    Angulo = 0
    
    
    Set ent1 = selectPLObj
    Set ent2 = selectPLObj
    
    
    ReDim ents(0) As AcadEntity
    Set ents(0) = ent1
    
    regs = ThisDrawing.ModelSpace.AddRegion(ents)
    Set reg1 = regs(0)
    
    Set ents(0) = ent2
    regs = ThisDrawing.ModelSpace.AddRegion(ents)
    Set reg3 = regs(0)
    
    
    reg3.Boolean acIntersection, reg1       'reg3 intersection
    
    
    Set ents(0) = ent1
    regs = ThisDrawing.ModelSpace.AddRegion(ents)
    Set reg1 = regs(0)
    
    Set ents(0) = ent2
    regs = ThisDrawing.ModelSpace.AddRegion(ents)
    Set reg2 = regs(0)
    
    ent1.Delete
    ent2.Delete
    
    reg2.Boolean acSubtraction, reg3
    
    
    
    expoldeRegion reg2
    
    expoldeRegion reg1
     
    
    Debug.Print ""
    
 
    
End Sub


Sub test110()

    Dim boundary As New ClsBoundary
    
    boundary.selects
    
    

End Sub

Sub test111()

    Dim selec1 As New ClsSelEntity
    Dim pt1 As New clsPoint
    
    Dim ent As AcadEntity
    
    selec1.selectPolyline ("#Get Polyline 1: ")
    
    Set ent = selec1.getEntity
    Set pt1 = selec1.getPoint
    
    addVertexT ent, pt1.x, pt1.y
    
    Debug.Print ""
    


End Sub

Sub test112()
    Dim selec1 As New ClsSelEntity
    Dim ent As AcadEntity
    Dim b As Boolean
    
    selec1.selectPolyline ("#Get Polyline 1: ")
    
    Set ent = selec1.getEntity
    
    b = hasProperties(ent)
    Debug.Print ent.layer & " extenal properties ===>>" & b
    
    
    
    
End Sub

 


Sub test114()

    Dim tn As New ClsTunnel
    
    tn.load

End Sub


Sub test115()

    Dim selec As New clsSelSets
    Dim ent As AcadEntity
    Dim ptd1() As Double
    Dim pt1 As New clsPoint
    Dim ptprev As New clsPoint
    Dim ptnext As New clsPoint
    Dim pr As New clsPolygonReader
    Dim alpha As Double
    Dim ddd(3) As Double
    Dim dddd() As Double
    Dim crossline As AcadEntity
    Dim intersd() As Double
    
    Set ent = selec.selectPolyline
    
    ptd1 = ThisDrawing.Utility.getPoint(, "Enter a point1: ")
    
    
    ptd1 = addVertex(ent, ptd1(0), ptd1(1))
    
    pt1.initPt ptd1
    
    pr.init ent
    pr.setIndexByPoint pt1
    pr.setIndex pr.getSIndex
    
    addDonut5 pt1.x, pt1.y
    
    Set ptprev = pr.prevPoint
    Set ptnext = pr.nextPoint
    Set ptnext = pr.nextPoint
    
    ddd(0) = ptprev.x
    ddd(1) = ptprev.y
    ddd(2) = ptnext.x
    ddd(3) = ptnext.y
    
    Set crossline = ThisDrawing.ModelSpace.AddLightWeightPolyline(ddd)
    crossline.color = acRed
    
    
    
    
    ReDim ptd1(2) As Double
    ptd1(0) = pt1.x
    ptd1(1) = pt1.y
    crossline.Rotate ptd1, PI / 2
    
    dddd = crossline.Coordinates
    crossline.Delete
    
    Set crossline = extendLineBoth(dddd(0), dddd(1), dddd(2), dddd(3), ptd1(0), ptd1(1), 50)
    
    
    intersd = ent.IntersectWith(crossline, acExtendNone)
    
    dddd = getNearestTwo(intersd, pt1.x, pt1.y)
    
    
    Debug.Print ""

End Sub


Sub test116()
    
    Dim filepath As String
    filepath = "D:\test.txt"

    Open filepath For Append As 1
    Write #1, "test"
    
    Close 1
    
     
End Sub

Sub test117()

    Dim ents() As AcadEntity
    Dim ent As AcadEntity
    Dim selec As New clsSelSets
    Dim pre As New ClsPolylineParkingEx
    Dim repeat As Boolean
    Dim dir As String
    
    Dim size As Integer
    
    
    ents = selectObjs

    dir = ThisDrawing.Utility.GetString(False, "방향(Default: Left): L or R")
    
    size = UBound(ents)
    For i = 0 To size
        Set ent = ents(i)
        
        repeat = True
        
        pre.init ent
        If dir = "R" Or dir = "r" Then
            pre.setRight
        End If
        pre.setdistance 2.5
        
        Do While (repeat)
        
            repeat = pre.addcrossline
        
        Loop
        
        pre.dispose
    Next


   
    
End Sub


Sub test118()
    Dim ents() As AcadEntity
    Dim ent As AcadEntity
    
    Dim ddd() As Double
    Dim ret() As Double
    
    Dim size As Integer
    
    ents = selectObjs
    size = UBound(ents)
    
    
    
    
    For i = 0 To size
        Set ent = ents(i)
        ddd = ent.Coordinates
 
        ret = reversePoint2d(ddd)
        
        ThisDrawing.ModelSpace.AddLightWeightPolyline ret
        ent.Delete
    Next
 
   


End Sub

Sub test119()

    Dim pk As New ClsParkingLot
    
    pk.loadEx
    

End Sub


Public Sub test120()
    Dim Region As Variant
    Dim Objeto(0) As AcadEntity
    Dim selEntidad As AcadEntity
    Dim Solido As Acad3DSolid
    Dim Punto As Variant
    Dim Punto2 As Variant
    Dim Altura As Double
    Dim Angulo As Double
    
    Dim ent1 As AcadEntity
    Dim ent2 As AcadEntity
    
    Dim reg1 As AcadRegion
    Dim reg2 As AcadRegion
    Dim reg3 As AcadRegion
    
    Dim intent As AcadEntity
    Dim intent2 As AcadLWPolyline
    
    Dim temp As AcadRegion
    Dim temp2 As AcadRegion
    Dim ttt As Variant
    
    Dim regs() As AcadRegion
    
    Dim conv As New ClsConverter
    Dim plroad() As AcadEntity
    
    Dim ents() As AcadEntity
    Dim hasRegion As Boolean
    
    Dim idx As Integer
    
    Dim size As Integer
    Dim cnt As Integer
    
    Altura = 10
    Angulo = 0
    
    
    plroad = selectPolylineObs
    
    size = UBound(plroad)
    
    
    For i = 0 To size
        Set ent1 = plroad(i)
        If ent1.Closed = True Then
            cnt = cnt + 1
        End If
    Next i
    
    
    ReDim regs(cnt - 1) As AcadRegion
    
    idx = 0
    
    For i = 0 To size
        Set ent1 = plroad(i)
        ReDim ents(0) As AcadEntity
        Set ents(0) = ent1
        
        If ent1.Closed = True Then
            ttt = ThisDrawing.ModelSpace.AddRegion(ents)
            Set regs(idx) = ttt(0)
            idx = idx + 1
        End If
        
    Next i
    
    Set reg1 = regs(0)
    
    For i = 1 To cnt - 1
        regs(0).Boolean acUnion, regs(i)
         
    Next i
    
    expoldeRegion regs(0)
     
End Sub


Public Sub test121()
    Dim plroad() As AcadEntity
    Dim ent As AcadEntity
    Dim size As Integer
    
    Dim pr As New clsPolygonReader
    
    plroad = selectPolylineObs
    
    size = UBound(plroad)
    
    For i = 0 To size
        Set ent = plroad(i)
        pr.init ent
        pr.findWeiredLine
    Next i
    
      
    
    
End Sub

Sub roundEdge()

    
    Dim er As New ClsEdgeRounder
    er.load
     

End Sub





Public Sub test400()

    Dim ss As New clsSelSets
    Dim textObj As AcadText
    Dim pt(2) As Double
    
    Set textObj = ss.selectAnything
    
    pt(0) = textObj.insertionPoint(0)
    pt(1) = textObj.insertionPoint(1)
    
    textObj.Alignment = acAlignmentMiddleCenter
    textObj.TextAlignmentPoint = pt
    
    
    Debug.Print ""

End Sub


Public Sub test401()
   Dim Text As AcadText
   Dim curnam As String
   Dim inpt(0 To 2) As Double
   Dim ht As Double
   
   curnam = "This is a string"
   inpt(0) = 5
   inpt(1) = 5
   inpt(2) = 0
  
   ht = 0.5
   
   Set Text = ThisDrawing.ModelSpace.AddText(curnam, inpt, ht)
   Text.Alignment = acAlignmentMiddleCenter
   'Text.TextAlignmentPoint = inpt
End Sub



Public Sub DrawPointsFromTextFile()
    Dim fd As Long
    Dim sline As String
    Dim ar As Variant
    
    fd = FreeFile
    
    Open "C:\Temp\Coordinates.txt" For Input Access Read Shared As fd
    
    Do Until EOF(fd)
    
        Line Input #fd, sline
        ar = Split(sline, ",")
        
        ReDim pt(UBound(ar)) As Double
        Dim i As Integer
        For i = 0 To UBound(ar)
            pt(i) = CDbl(ar(i))
        Next i
        ThisDrawing.ModelSpace.AddPoint pt
    Loop
    
    Close fd
End Sub

Sub testfilewriter()

 
    Dim fso As Object
    Dim strpath As String
    
    
    strpath = "DAWUL_CAD_SETTINGS.txt"
    Set fso = CreateObject("Scripting.FileSystemObject")
    Dim oFile As Object
    Set oFile = fso.CreateTextFile(strpath)
    oFile.WriteLine "test1"
    oFile.WriteLine "test2"
    oFile.Close
    Set fso = Nothing
    Set oFile = Nothing
End Sub


Sub testfilereader()

 
    Dim fso As Object
    Dim strpath As String
    Dim myFileText As String
    
    
    strpath = "DAWUL_CAD_SETTINGS.txt"
    Set fso = CreateObject("Scripting.FileSystemObject")
    
    Dim oFile As Object
    Set oFile = fso.OpenTextFile(strpath, 1) '1: reading, 2: Writing, 3: appending
     
    ' You can also read it line by line
    Dim line As String
    While Not oFile.AtEndOfStream ' while we are not finished reading through the file
        line = oFile.ReadLine
        ' do something with the line...
        Debug.Print line
    Wend
    oFile.Close
    
    
    Set fso = Nothing
    Set oFile = Nothing
End Sub
 


Sub Example_SetBulge()
    ' This example creates a lightweight polyline in model space.
    ' It then finds and changes the bulge for a given segment.
    
    Dim plineObj As AcadLWPolyline
    Dim points(0 To 11) As Double
    
    ' Define the 2D polyline points
    points(0) = 1: points(1) = 1
    points(2) = 1: points(3) = 2
    points(4) = 2: points(5) = 2
    points(6) = 3: points(7) = 2
    points(8) = 4: points(9) = 4
    points(10) = 4: points(11) = 1
        
    ' Create a lightweight Polyline object in model space
    Set plineObj = ThisDrawing.ModelSpace.AddLightWeightPolyline(points)
    ZoomAll
    
    ' Find the bulge of the third segment
    Dim currentBulge As Double
    currentBulge = plineObj.GetBulge(3)
    MsgBox "The bulge for the third segment is " & plineObj.GetBulge(3), , "SetBulge Example"
    
    ' Change the bulge of the third segment
    plineObj.SetBulge 2, -1
    plineObj.Update
    MsgBox "The bulge for the third segment is now " & plineObj.GetBulge(3), , "SetBulge Example"
    
End Sub
 
Sub Ch10_CreatingAnAttribute()
 ' Define the block
 Dim blockObj As AcadBlock
 Dim insertionPnt(0 To 2) As Double
 insertionPnt(0) = 0
 insertionPnt(1) = 0
 insertionPnt(2) = 0
 Set blockObj = ThisDrawing.Blocks.add(insertionPnt, "BlockWithAttribute")
 
 
 ' Add an attribute to the block
 Dim attributeObj As AcadAttribute
 Dim height As Double
 Dim mode As Long
 Dim prompt As String
 Dim insertionPoint(0 To 2) As Double
 Dim tag As String
 Dim value As String
 height = 1
 mode = acAttributeModeVerify
 prompt = "New Prompt"
 insertionPoint(0) = 5
 insertionPoint(1) = 5
 insertionPoint(2) = 0
 tag = "New Tag"
 value = "New Value"
 Set attributeObj = blockObj.AddAttribute(height, mode, prompt, insertionPoint, tag, value)
 ' Insert the block, creating a block reference
 ' and an attribute reference
 Dim blockRefObj As AcadBlockReference
 insertionPnt(0) = 2
 insertionPnt(1) = 2
 insertionPnt(2) = 0
 Set blockRefObj = ThisDrawing.ModelSpace.InsertBlock(insertionPnt, "BlockWithAttribute", 1#, 1#, 1#, 0)
End Sub

Attribute VB_Name = "chamferModule"


Function findVertexAtLine(ent As AcadEntity, ent2 As AcadLine) As Double()

    Dim ddd(0 To 3) As Double
    Dim filletpoint(0 To 7) As Double   '8
        
    
    
    ddd(0) = ent2.startPoint(0)
    ddd(1) = ent2.startPoint(1)
    ddd(2) = ent2.endPoint(0)
    ddd(3) = ent2.endPoint(1)
            
    count = UBound(ddd)
    
    vx = ddd(count - 1)
    vy = ddd(count)
    
    newp = addVertex(ent, vx, vy)
    
    If newp(0) <> 0 And newp(1) <> 0 Then
    
        filletpoint(index) = newp(0)
        index = index + 1
        filletpoint(index) = newp(1)
        index = index + 1
         
    Else
        vx = ddd(0)
        vy = ddd(1)
        
        newp = addVertex(ent, vx, vy)
        
        If newp(0) <> 0 And newp(1) <> 0 Then
        
            filletpoint(index) = newp(0)
            index = index + 1
            filletpoint(index) = newp(1)
            index = index + 1
        End If
    End If
    
    findVertexAtLine = newp

End Function

Function findVertexAtLine2(ent As AcadEntity, ent2 As AcadLine, pt As clsPoint) As Double()

    Dim filletpoint(0 To 7) As Double   '8
    Dim nv() As Double
    
    nv = getNearestVertexAtLine(ent2, pt)
    vx = nv(0)
    vy = nv(1)
    
    newp = addVertex2(ent, vx, vy)
    
    If newp(0) <> 0 And newp(1) <> 0 Then
    
        filletpoint(index) = newp(0)
        index = index + 1
        filletpoint(index) = newp(1)
        index = index + 1
   
    End If
    
    findVertexAtLine2 = newp

End Function


Function getNearestVertexAtLine(ent2 As AcadLine, ref As clsPoint) As Double()

    Dim ent2d() As Double
    Dim x1, y1, x2, y2 As Double
    
    Dim dist1, dist2 As Double
    Dim ret(0 To 1) As Double
    
    
    x1 = ent2.startPoint(0)
    y1 = ent2.startPoint(1)
    x2 = ent2.endPoint(0)
    y2 = ent2.endPoint(1)
    
    'addDonutA x1, y1
    'addDonutA x2, y2
        
    dist1 = getDistance(x1, y1, ref.x, ref.y)
    dist2 = getDistance(x2, y2, ref.x, ref.y)
    
    If dist1 > dist2 Then
        ret(0) = x2
        ret(1) = y2
    Else
        ret(0) = x1
        ret(1) = y1
    End If
    
    getNearestVertexAtLine = ret


End Function

Attribute VB_Name = "clsChamfer2"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private orgLayer As String
Private oldroad As AcadEntity
Private newroad As AcadEntity
Private fillet As AcadEntity

Private ptIntersection As Variant

Private isEdited As Boolean


Public Function load()

    Dim pt1 As New clsPoint
    Dim retLine As AcadLine
    Dim tmp As Variant
    
    
    Dim np1 As New clsPoint
    Dim np2 As New clsPoint
    Dim np3 As New clsPoint
     
    Dim pr As New clsPolygonReader
    
    Dim newroadsplit() As Double
    Dim oldroadsplit() As Double
    Dim additionsplit(0 To 3) As Double
    
    Dim merge As New ClsMerger
    Dim resultd() As Double
    Dim result As AcadEntity
    Dim test As Boolean
    
    
    Dim pt3 As New clsPoint
    
    
    Dim line1 As AcadLine
    Dim line2 As AcadLine
    
    Dim pr1 As New clsPolygonReader
    Dim pr2 As New clsPolygonReader
    
    
    Dim selec1 As New ClsSelEntity
    Dim selec2 As New ClsSelEntity
    Dim undoPoint As AcadEntity
    
    Dim seler As New ClsSelReal
    Dim frad As Double
    
    Dim selecs As New clsSelSets
    
    Dim okcnt As Integer
    Dim ok As Boolean
    
    isEdited = False
    okcnt = 0
    
    ok = selec1.selectPolyline("#Get Polyline 1: ")
    Set newroad = selec1.getEntity
    Set pt1 = selec1.getPoint

    
    If ok = False Then
        ThisDrawing.Utility.prompt "선택에 오류가 발생했습니다."
        GoTo EndOfFunction
    
    End If
    
    Set undoPoint = ThisDrawing.ModelSpace.AddText("UU-U", selec1.getMovePoindD(5), 2)
    
    ok = selec2.selectPolyline("#Get Polyline 2: ")
    Set oldroad = selec2.getEntity
    Set pt3 = selec2.getPoint
    
        
    If ok = False Then
        ThisDrawing.Utility.prompt "선택에 오류가 발생했습니다."
        GoTo EndOfFunction
    
    End If
    
    
    isEdited = hasProperties(newroad)
    
    ptIntersection = searchCrossVertext(newroad, oldroad)
    
    For i = 0 To UBound(ptIntersection) Step 3
        'addDonutA ptIntersection(i), ptIntersection(i + 1)          '!!!!!!!!!!!!!!!!!!!!!!
        
        ok = isContains(newroad, CDbl(ptIntersection(i)), CDbl(ptIntersection(i + 1)))
        If ok = True Then
            okcnt = okcnt + 1
        End If
    Next i
    
    
    If okcnt < 2 Then
        ThisDrawing.Utility.prompt "인접부분 확인바랍니다 - 접점: " & okcnt
        GoTo EndOfFunction
    
    End If
    
    
    Set np3 = getNearPoint2(ptIntersection, pt3)
    
    'addDonut5 np3.x, np3.y
    
    
    pr1.init newroad
    Set line1 = pr1.getLine(pt1)
    
     
    pr2.init oldroad
    Set line2 = pr2.getLine(pt3)
    
     
    
    Set resultpl = getShortestLine(line2, pt3, np3)
    
    
    frad = seler.selectChamferDistance
    
    
    Application.ActiveDocument.SendCommand "_chamfer" & vbCr & "D" & vbCr & frad & vbCr & frad & vbCr & "(HandEnt """ & line1.Handle & """)" & vbCr & "(HandEnt """ & resultpl.Handle & """)" & vbCr
    'Application.ActiveDocument.SendCommand "_fillet" & vbCr & "T" & vbCr & "N" & vbCr & "r" & vbCr & frad & vbCr & "(HandEnt """ & line1.Handle & """)" & vbCr & "(HandEnt """ & resultpl.Handle & """)" & vbCr
    
    Set retLine = selecs.selectLine
    
    If line2.Handle <> resultpl.Handle Then
        resultpl.Delete
    End If
    
    line1.Delete
    line2.Delete
    
    
    
    Debug.Print "chamfer created"
  
    
    
    newp1 = findVertexAtLine2(newroad, retLine, pt1)   '아크와 도로(새도로)의 접점 추가
    newp2 = findVertexAtLine2(oldroad, retLine, pt3)   '아크와 도로(구도로)의 접점 추가
   
   
    np1.initXy newp1(0), newp1(1)
    np2.initXy newp2(0), newp2(1)
    
    
    Debug.Print "np1: " & np1.x & ", " & np1.y
    Debug.Print "np2: " & np2.x & ", " & np2.y
   
    'addDonutA np1.x, np1.y
    'addDonutA np2.x, np2.y
   
   
    additionsplit(0) = np1.x
    additionsplit(1) = np1.y
    additionsplit(2) = np2.x
    additionsplit(3) = np2.y
    
   
    Set np3 = getFarPoint2Ex(newroad, ptIntersection, np1)     '기존도로 아크 접점에서 먼 지점을 찾는다
    
    
    addVertex oldroad, np3.x, np3.y     '기존도로에 접점추가
    

   
    Debug.Print "cross point created"
    
    pr.init newroad
    pr.setIndexByPoint np1
    pr.checkDirection pt3
    
    'addDonut5 np3.x, np3.y
    'addDonut5 np1.x, np1.y
    Debug.Print "newroad direction processed"
    
    sidx = pr.setIndexByPoint(np1)
    eidx = pr.setEIndexByPoint(np3)
    
    newroadsplit = pr.getLongLine2()
    'newroadsplit = pr.splitInnerLine(np3, np1)
    'addLine newroadsplit
    
    Debug.Print "newroad split created"
   
    pr.init oldroad
    pr.setIndexByPoint np2
    pr.checkDirection pt1
    
    Debug.Print "oldroad direction processed"
    
    sidx = pr.setIndexByPoint(np2)
    eidx = pr.setEIndexByPoint(np3)
    
    oldroadsplit = pr.getShortLine2()
    'oldroadsplit = pr.splitInnerLine(np2, np3)
    'addLine oldroadsplit
    
   
    Debug.Print "oldroad split created"
        
    size1 = UBound(newroadsplit)
    size2 = UBound(additionsplit)
    size3 = UBound(oldroadsplit)
    
    merge.setSize size1 + size2 + size3 + 2
    
    
    merge.add newroadsplit
    merge.add additionsplit
    merge.add oldroadsplit
    
    
    Set result = addLine(merge.getMerged)
    result.Closed = True
    'newroad.Delete
    retLine.Delete
    
    'ThisDrawing.SendCommand "sob" & vbCr
    
    orgLayer = newroad.layer
    result.layer = getAddLayerName(orgLayer)
    newroad.layer = getDelLayerName(orgLayer)
    
    If (orgLayer Like LYR_ADD & "*") Or isEdited = False Then
        newroad.Delete
    End If
    
EndOfFunction:
    If undoPoint Is Nothing = False Then
        undoPoint.Delete
    End If
    Debug.Print "DONE"
    
End Function

Attribute VB_Name = "clsFillet"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private orgLayer As String
Private oldroad As AcadEntity
Private newroad As AcadEntity
Private fillet As AcadEntity

Private ptIntersection As Variant
    
Private np1 As New clsPoint
Private np2 As New clsPoint
Private np3 As New clsPoint


Private newroadsplit() As Double
Private oldroadsplit() As Double
Private filletsplit() As Double

Private tmpf As AcadLWPolyline


Private isEdited As Boolean






Public Function load()

    Dim pt1 As New clsPoint
    Dim p2() As Double
    Dim pt3 As New clsPoint
    Dim retArc As AcadEntity
    Dim tmp As Variant
     
    Dim pr As New clsPolygonReader
    
    Dim merge As New ClsMerger
    Dim resultd() As Double
    Dim result As AcadEntity
    Dim test As Boolean
    
    Dim selec1 As New ClsSelEntity
    Dim selec2 As New ClsSelEntity
    Dim undoPoint As AcadEntity
    
    Dim seler As New ClsSelReal
    Dim frad As Double
    
    Dim selecs As New clsSelSets
    Dim okcnt As Integer
    
    Dim ok As Boolean
    
    On Error GoTo EndOfFunction
    Debug.Print "==================START ================="
    
    isEdited = False
    okcnt = 0
    
    ok = selec1.selectPolyline("#Get Polyline 1: ")
    
    If ok = False Then
        ThisDrawing.Utility.prompt "선택에 오류가 발생했습니다."
        GoTo EndOfFunction
    
    End If
    
    Set newroad = selec1.getEntity
    Set pt1 = selec1.getPoint
    
    Set undoPoint = ThisDrawing.ModelSpace.AddText("UU-U", selec1.getMovePoindD(5), 2)
    
    ThisDrawing.SetVariable "osmode", 0
    p2 = ThisDrawing.Utility.getPoint(, "#Enter a point2: ")
    
    ok = selec2.selectPolyline("#Get Polyline 3: ")
    
    If ok = False Then
        ThisDrawing.Utility.prompt "선택에 오류가 발생했습니다."
        GoTo EndOfFunction
    
    End If
    
    Set oldroad = selec2.getEntity
    Set pt3 = selec2.getPoint
    
    
    isEdited = hasProperties(newroad)
    
    
    
    Debug.Print "pt1.x = " & pt1.x
    Debug.Print "pt1.y = " & pt1.y
    Debug.Print "p2(0) = " & p2(0)
    Debug.Print "p2(1) = " & p2(1)
    Debug.Print "pt3.x = " & pt3.x
    Debug.Print "pt3.y = " & pt3.y
   
   
'pt1.x = 1145362.93863217
'pt1.y = 1682156.83027352
'p2(0) = 1145360.47148013
'p2(1) = 1682157.86296715
'pt3.x = 1145358.17302185
'pt3.y = 1682156.97780121
   
     
    ptIntersection = searchCrossVertext(newroad, oldroad)
        
    For i = 0 To UBound(ptIntersection) Step 3
        'addDonutA ptIntersection(i), ptIntersection(i + 1)          '!!!!!!!!!!!!!!!!!!!!!!
        
        ok = isContains(newroad, CDbl(ptIntersection(i)), CDbl(ptIntersection(i + 1)))
        If ok = True Then
            okcnt = okcnt + 1
        End If
    Next i
    
    
    If okcnt < 2 Then
        ThisDrawing.Utility.prompt "인접부분 확인바랍니다 - 접점: " & okcnt
        GoTo EndOfFunction
    
    End If
   
    
    Set retArc = getArcBy3P(pt1.getPoints(), p2, pt3.getPoints()) '세점을 지나는 아크를 생성
    Set fillet = arc2line(retArc)  '아크를 라인으로 변경
    
    ThisDrawing.SendCommand "sob" & vbCr
    
    filletsplit = fillet.Coordinates
    
    retArc.Delete
    
    Debug.Print "fillet created"
    
  
    
  
    
    
    newp1 = findVertex2(newroad, fillet, pt1)   '아크와 도로(새도로)의 접점 추가
    newp2 = findVertex2(oldroad, fillet, pt3)   '아크와 도로(구도로)의 접점 추가
   
   
    np1.initXy newp1(0), newp1(1)
    np2.initXy newp2(0), newp2(1)
    
    
    Debug.Print "np1: " & np1.x & ", " & np1.y
    Debug.Print "np2: " & np2.x & ", " & np2.y
    
    'addDonutB np1.x, np1.y
    'addDonutB np2.x, np2.y
    
   
    Set np3 = getFarPoint2Ex(newroad, ptIntersection, np1)     '기존도로 아크 접점에서 먼 지점을 찾는다
    
    ptIntersection = searchCrossVertext(newroad, fillet)
  
    If UBound(ptIntersection) > 0 Then
        Set np1 = getNearPoint2(ptIntersection, np3)
        addVertex fillet, np1.x, np1.y
        'addDonutA np1.x, np1.y
    End If
    
    ptIntersection = searchCrossVertext(oldroad, fillet)
  
    If UBound(ptIntersection) > 0 Then
        Set np2 = getNearPoint2(ptIntersection, np3)
        addVertex fillet, np2.x, np2.y
        'addDonutA np2.x, np2.y
    End If
    
    filletsplit = fillet.Coordinates
    
    
    addVertex oldroad, np3.x, np3.y     '기존도로에 접점추가
    addVertex oldroad, np2.x, np2.y
    addVertex newroad, np1.x, np1.y
    
    'addDonutA np1.x, np1.y
    'addDonutA np2.x, np2.y
    'addDonutA np3.x, np3.y
   
    Debug.Print "cross point created"
    
    pr.init newroad
    pr.setIndexByPoint np1
    pr.checkDirection pt3
    
    'addDonut5 np3.x, np3.y
    'addDonut5 np1.x, np1.y
    Debug.Print "newroad direction processed"
    
    sidx = pr.setIndexByPoint(np1)
    eidx = pr.setEIndexByPoint(np3)
    
    newroadsplit = pr.getLongLine2()
    
    Debug.Print "newroad split created"
   
    pr.init oldroad
    pr.setIndexByPoint np2
    pr.checkDirection pt1
    
    Debug.Print "oldroad direction processed"
    
    'addDonutA pt1.x, pt1.y
    'addDonutA np2.x, np2.y
    'addDonutA np3.x, np3.y
    
    sidx = pr.setIndexByPoint(np2)
    eidx = pr.setEIndexByPoint(np3)
    
    oldroadsplit = pr.getShortLine2()
    
    'oldroadsplit = pr.splitInnerLine(np2, np3)
    'addLine oldroadsplit
    
    
    
    Debug.Print "oldroad split created"
    
    checkTailPointEx np2
    checkLastPoint
    'oldroadsplit = checkCrossPoint3Ex(oldroad, oldroadsplit, np3)
    checkCrossPoint
    
    Debug.Print "oldroad split checked"
    
    checkTailPointEx np1
    checkLastPoint2
    'newroadsplit = checkCrossPoint4Ex(newroad, newroadsplit, np2)
    checkCrossPoint2
    
    Debug.Print "newroad split checked"
        
    size1 = UBound(newroadsplit)
    size2 = UBound(filletsplit)
    size3 = UBound(oldroadsplit)
    
    merge.setSize size1 + size2 + size3 + 2
    
    
    merge.add newroadsplit
    merge.add filletsplit
    merge.add oldroadsplit
    
    
    Set result = addLine(merge.getMerged)
    result.Closed = True
    'newroad.Delete
    fillet.Delete
    
    
    'Set temp = ThisDrawing.ActiveLayer
    
    orgLayer = newroad.layer
    result.layer = getAddLayerName(orgLayer)
    newroad.layer = getDelLayerName(orgLayer)
    
    If (orgLayer Like LYR_ADD & "*") Or isEdited = False Then
        newroad.Delete
    End If
    
EndOfFunction:
    If undoPoint Is Nothing = False Then
        undoPoint.Delete
    End If
    Debug.Print "DONE"
    
    
End Function


Private Function getArcBy3P(p1() As Double, p2() As Double, p3() As Double) As AcadArc
    Dim centerPoint(0 To 2) As Double
    Dim retOjb As AcadArc
    
    x1 = p1(0)
    y1 = p1(1)
    
    x2 = p2(0)
    y2 = p2(1)
     
    x3 = p3(0)
    y3 = p3(1)
    
    d1 = (x2 - x1) / (y2 - y1)
    d2 = (x3 - x2) / (y3 - y2)
    
    cx = ((y3 - y1) + (x2 + x3) * d2 - (x1 + x2) * d1) / (2 * (d2 - d1))
    cy = -d1 * (cx - (x1 + x2) / 2) + (y1 + y2) / 2
     
    r = VBA.Sqr((x1 - cx) ^ 2 + (y1 - cy) ^ 2)
    
    centerPoint(0) = cx
    centerPoint(1) = cy
    
    StartAngle = ArcTan2((x1 - cx), (y1 - cy))
    EndAngle = ArcTan2((x3 - cx), (y3 - cy))
    
    If StartAngle >= 0 And EndAngle >= 0 Then
        If StartAngle > EndAngle Then
            tmp = StartAngle
            StartAngle = EndAngle
            EndAngle = tmp
        End If
    ElseIf StartAngle < 0 And EndAngle < 0 Then
        If StartAngle > EndAngle Then
            tmp = StartAngle
            StartAngle = EndAngle
            EndAngle = tmp
        End If
    ElseIf StartAngle > 0 And EndAngle < 0 Then
        If (PI - StartAngle) + (PI + EndAngle) > PI Then
            tmp = StartAngle
            StartAngle = EndAngle
            EndAngle = tmp
        End If
    ElseIf StartAngle < 0 And EndAngle > 0 Then
        If Abs(StartAngle) + EndAngle > PI Then
            tmp = StartAngle
            StartAngle = EndAngle
            EndAngle = tmp
        End If
            
    End If
    
    
    Set retOjb = ThisDrawing.ModelSpace.AddArc(centerPoint, r, StartAngle, EndAngle)
     
    
    Set getArcBy3P = retOjb

End Function


Function checkTailPointEx(pt As clsPoint)
    
    Dim idx As Integer
    Dim lastx As Double
    Dim lasty As Double
    Dim size As Integer
    Dim dist1 As Double
    Dim dist2 As Double
    Dim x As Double
    Dim y As Double
    Dim ret() As Double
    
    size = UBound(filletsplit)
    
    lastx = filletsplit(size - 1)
    lasty = filletsplit(size)

    dist1 = getDistance(pt.x, pt.y, lastx, lasty)
    
    lastx = filletsplit(0)
    lasty = filletsplit(1)
    
    dist2 = getDistance(pt.x, pt.y, lastx, lasty)
    
    
    'addDonutA np1.x, np1.y
    
    If dist1 < dist2 Then
        For i = size - 1 To 0 Step -2
            x = filletsplit(i)
            y = filletsplit(i + 1)
            
            If x = pt.x And y = pt.y Then
            
                Debug.Print ""
                Exit For
                
            End If
            idx = idx - 2
            
        Next i
    
    Else
        
        
        For i = 0 To size Step 2
            x = filletsplit(i)
            y = filletsplit(i + 1)
            
            'addDonut5 x, y
            
            'Debug.Print "*" & pt.x & ", " & pt.y
            'Debug.Print "+" & x & ", " & y
            
            b1 = (x = pt.x)
            b2 = (y = pt.y)
            
            If isEqualsDouble(x, y, pt.x, pt.y) Then
            
                Debug.Print ""
                Exit For
                
            End If
            idx = idx + 2
        
        Next i
        
        If idx < size Then
            ReDim ret(size - idx) As Double
            
            For i = idx To size Step 2
            
                ret(i - idx) = filletsplit(i)
                ret(i - idx + 1) = filletsplit(i + 1)
                Debug.Print ""
            Next i
            
            filletsplit = ret
        End If
    
    
    End If
  
    
End Function

Function checkTailPoint()
    
    Dim idx As Integer
    Dim lastx As Double
    Dim lasty As Double
    Dim size As Integer
    Dim dist1 As Double
    Dim dist2 As Double
    Dim x As Double
    Dim y As Double
    Dim ret() As Double
    
    size = UBound(filletsplit)
    
    lastx = filletsplit(size - 1)
    lasty = filletsplit(size)

    dist1 = getDistance(np1.x, np1.y, lastx, lasty)
    
    lastx = filletsplit(0)
    lasty = filletsplit(1)
    
    dist2 = getDistance(np1.x, np1.y, lastx, lasty)
    
    
    'addDonutA np1.x, np1.y
    
    If dist1 < dist2 Then
        For i = size - 1 To 0 Step -2
            x = filletsplit(i)
            y = filletsplit(i + 1)
            
            If x = np1.x And y = np1.y Then
            
                Debug.Print ""
                Exit For
                
            End If
            idx = idx - 2
            
        Next i
    
    Else
        
        
        For i = 0 To size Step 2
            x = filletsplit(i)
            y = filletsplit(i + 1)
            
            'addDonut5 x, y
            
            Debug.Print "*" & np1.x & ", " & np1.y
            Debug.Print "+" & x & ", " & y
            
            b1 = (x = np1.x)
            b2 = (y = np1.y)
            
            If isEqualsDouble(x, y, np1.x, np1.y) Then
            
                Debug.Print ""
                Exit For
                
            End If
            idx = idx + 2
        
        Next i
        
        If idx < size Then
            ReDim ret(size - idx) As Double
            
            For i = idx To size Step 2
            
                ret(i - idx) = filletsplit(i)
                ret(i - idx + 1) = filletsplit(i + 1)
                Debug.Print ""
            Next i
            
            filletsplit = ret
        End If
    
    
    End If
  
    
End Function

 
 Function checkLastPoint()

    Dim retvalue() As Double
    Dim lastx As Double
    Dim lasty As Double
    Dim size As Integer
    Dim dist1 As Double
    Dim dist2 As Double
    
    size = UBound(filletsplit)
    
    lastx = filletsplit(size - 1)
    lasty = filletsplit(size)
    
    'addDonut5 lastx, lasty
    'addDonutA np2.x, np2.y

    dist1 = getDistance(np2.x, np2.y, lastx, lasty)
    
    lastx = filletsplit(0)
    lasty = filletsplit(1)
    
    dist2 = getDistance(np2.x, np2.y, lastx, lasty)
    
    
    If dist1 <> 0 And dist2 <> 0 Then   '겹치지 않을때
    
        If dist1 < dist2 Then
            filletsplit(size - 1) = np2.x
            filletsplit(size) = np2.y
        
        Else
            filletsplit(0) = np2.x
            filletsplit(1) = np2.y
        
        End If
  
    End If
  
End Function



Function checkLastPoint2()  '

    Dim retvalue() As Double
    Dim firstx As Double
    Dim firsty As Double
    Dim size As Integer
    Dim dist1 As Double
    Dim dist2 As Double
    
    size = UBound(filletsplit)
    
    firstx = filletsplit(size - 1)
    firsty = filletsplit(size)
    
    'addDonut5 firstx, firsty
    'addDonutA np1.x, np1.y

    dist1 = getDistance(np1.x, np1.y, firstx, firsty)
    
    firstx = filletsplit(0)
    firsty = filletsplit(1)
    
    dist2 = getDistance(np1.x, np1.y, firstx, firsty)
    
    
    If dist1 <> 0 And dist2 <> 0 Then   '겹치지 않을때
    
        If dist1 < dist2 Then
            filletsplit(size - 1) = np1.x
            filletsplit(size) = np1.y
        
        Else
            filletsplit(0) = np1.x
            filletsplit(1) = np1.y
        
        End If
  
    End If
  
End Function
 
 
Function checkCrossPoint()


    Dim tmpfillet As AcadLWPolyline
    Dim tmpoldroad As AcadLWPolyline
    Dim intersec As Variant
    
    Dim selidx As Integer
    Dim mindist As Double
    
    Dim plreader As New ClsPolylineReader
    
    Dim x, y As Double
    Dim nx As Double
    Dim ny As Double
    
    Dim b1, b2 As Boolean
    
    selidx = -1
    mindist = 99999
    
    Set tmpfillet = ThisDrawing.ModelSpace.AddLightWeightPolyline(filletsplit)
    Set tmpoldroad = ThisDrawing.ModelSpace.AddLightWeightPolyline(oldroadsplit)
    
    intersec = searchCrossVertext(tmpfillet, oldroad)
    
    'addDonutA np3.x, np3.y
    
    For i = 0 To UBound(intersec) Step 3
    
        x = intersec(i)
        y = intersec(i + 1)
    
        b1 = isContains(tmpfillet, CDbl(x), CDbl(y))
        b2 = isContains(tmpoldroad, CDbl(x), CDbl(y))
        
        
        'addDonut5 intersec(i), intersec(i + 1)
        
        If b1 = False Or b2 = False Then
            
        Else
        
            dist = getDistance(np3.x, np3.y, intersec(i), intersec(i + 1))
            
            
            
            If dist < mindist Then
            
                mindist = dist
                selidx = i
            End If
        
        End If
    Next i
    
    
    If selidx = -1 Then
        Return
    End If
    
    
    nx = intersec(selidx)
    ny = intersec(selidx + 1)
    
    'addDonutA nx, ny
    
    
    
    
    addVertex tmpfillet, nx, ny
    addVertex tmpoldroad, nx, ny
    
    plreader.init tmpfillet
    filletsplit = plreader.getLongDDLine(nx, ny)
    'Set tmpf = ThisDrawing.ModelSpace.AddLightWeightPolyline(filletsplit)
    'tmpf.color = acBlue
    
    plreader.init tmpoldroad
    oldroadsplit = plreader.getLongDDLine(nx, ny)
    'Set tmpf = ThisDrawing.ModelSpace.AddLightWeightPolyline oldroadsplit
    
    addVertex oldroad, nx, ny
    
    
    tmpfillet.Delete
    tmpoldroad.Delete
    
    
    Debug.Print ""
    
    
    
End Function

Function checkCrossPointEx()


    Dim tmpfillet As AcadLWPolyline
    Dim tmpoldroad As AcadLWPolyline
    Dim intersec As Variant
    
    Dim selidx As Integer
    Dim mindist As Double
    
    Dim plreader As New ClsPolylineReader
    
    Dim x, y As Double
    Dim nx As Double
    Dim ny As Double
    
    Dim b1, b2 As Boolean
    
    selidx = -1
    mindist = 99999
    
    Set tmpfillet = ThisDrawing.ModelSpace.AddLightWeightPolyline(filletsplit)
    Set tmpoldroad = ThisDrawing.ModelSpace.AddLightWeightPolyline(oldroadsplit)
    
    intersec = searchCrossVertext(tmpfillet, oldroad)
    
    For i = 0 To UBound(intersec) Step 3
    
        x = intersec(i)
        y = intersec(i + 1)
    
        'b1 = isContains(tmpfillet, CDbl(x), CDbl(y))
        'b2 = isContains(tmpoldroad, CDbl(x), CDbl(y))
        
        
        'addDonut5 intersec(i), intersec(i + 1)
        
                
        dist = getDistance(np3.x, np3.y, intersec(i), intersec(i + 1))
            
        If dist < mindist Then
            mindist = dist
            selidx = i
        End If
        
        
    Next i
    
    
    If selidx = -1 Then
        Return
    End If
    
    
    nx = intersec(selidx)
    ny = intersec(selidx + 1)
    
    'addDonutA nx, ny
    
    'b1 = isContains(tmpfillet, CDbl(x), CDbl(y))
    'b2 = isContains(tmpoldroad, CDbl(x), CDbl(y))
    
    
    np2.x = nx
    np2.y = ny
    
    addVertex tmpfillet, nx, ny
    addVertexT tmpoldroad, nx, ny
   
    'Set tmpf = sublwpolyline(nx, ny, tmpoldroad)
   
    plreader.init tmpfillet
    filletsplit = plreader.getLongDDLine(nx, ny)
    
    'Set tmpf = ThisDrawing.ModelSpace.AddLightWeightPolyline(filletsplit)
    'tmpf.color = acBlue
    
    plreader.init tmpoldroad
    oldroadsplit = plreader.getLongDDLine(nx, ny)
    'Set tmpf = ThisDrawing.ModelSpace.AddLightWeightPolyline(oldroadsplit)
    'tmpf.color = acRed
    
    tmpfillet.Delete
    tmpoldroad.Delete
    
    
    Debug.Print ""
    
    
    
End Function



Function checkCrossPoint2()


    Dim tmpfillet As AcadLWPolyline
    Dim tmpnewroad As AcadLWPolyline
    Dim intersec As Variant
    
    Dim selidx As Integer
    Dim mindist As Double
    
    Dim plreader As New ClsPolylineReader
    
    Dim x, y As Double
    Dim nx As Double
    Dim ny As Double
    
    Dim b1, b2 As Boolean
    
    selidx = -1
    mindist = 99999
    
    Set tmpfillet = ThisDrawing.ModelSpace.AddLightWeightPolyline(filletsplit)
    Set tmpnewroad = ThisDrawing.ModelSpace.AddLightWeightPolyline(newroadsplit)
    
    intersec = searchCrossVertext(tmpfillet, newroad)
    
    'addDonut5 np2.x, np2.y
    
    For i = 0 To UBound(intersec) Step 3
    
        x = intersec(i)
        y = intersec(i + 1)
    
        b1 = isContains(tmpfillet, CDbl(x), CDbl(y))
        b2 = isContains(tmpnewroad, CDbl(x), CDbl(y))
        
        If b1 = False Or b2 = False Then
            
        Else
        
            dist = getDistance(np2.x, np2.y, intersec(i), intersec(i + 1))
            
            'addDonutA intersec(i), intersec(i + 1)
            
            If dist < mindist Then
            
                mindist = dist
                selidx = i
            End If
        
        End If
    Next i
    
    
    If selidx = -1 Then
        Return
    End If
    
    
    nx = intersec(selidx)
    ny = intersec(selidx + 1)
    
    'addDonutA nx, ny
    
    
    
    
    addVertex tmpfillet, nx, ny
    addVertex tmpnewroad, nx, ny
    
    plreader.init tmpfillet
    filletsplit = plreader.getLongDDLine(nx, ny)
    'ThisDrawing.ModelSpace.AddLightWeightPolyline filletsplit
    
    plreader.init tmpnewroad
    newroadsplit = plreader.getLongDDLine(nx, ny)
    'ThisDrawing.ModelSpace.AddLightWeightPolyline oldroadsplit
    
    addVertex newroad, nx, ny
    
    
    tmpfillet.Delete
    tmpnewroad.Delete
    
    
    Debug.Print ""
    
    
    
End Function



Function checkCrossPoint3Ex(road As AcadEntity, roadsplit() As Double, np As clsPoint) As Double()


    Dim tmpfillet As AcadLWPolyline
    Dim tmproad As AcadLWPolyline
    Dim intersec As Variant
    
    Dim selidx As Integer
    Dim mindist As Double
    
    Dim plreader As New ClsPolylineReader
    
    Dim x, y As Double
    Dim nx As Double
    Dim ny As Double
    
    Dim b1, b2 As Boolean
    
    selidx = -1
    mindist = 99999
    
    Set tmpfillet = ThisDrawing.ModelSpace.AddLightWeightPolyline(filletsplit)
    Set tmproad = ThisDrawing.ModelSpace.AddLightWeightPolyline(roadsplit)
    
    intersec = searchCrossVertext(tmpfillet, road)
    
    'addDonut5 np.x, np.y
    
    For i = 0 To UBound(intersec) Step 3
    
        x = intersec(i)
        y = intersec(i + 1)
    
        'b1 = isContains(tmpfillet, CDbl(x), CDbl(y))
        'b2 = isContains(tmproad, CDbl(x), CDbl(y))
        
        
        dist = getDistance(np.x, np.y, intersec(i), intersec(i + 1))
            
        'addDonutA intersec(i), intersec(i + 1)
            
        If dist < mindist Then
            
            mindist = dist
            selidx = i
        End If
        
        
    Next i
    
    
    If selidx = -1 Then
        Return
    End If
    
    
    nx = intersec(selidx)
    ny = intersec(selidx + 1)
    
    'addDonutA nx, ny
    
    np2.x = nx
    np2.y = ny
    
    
    
    addVertex tmpfillet, nx, ny
    addVertexT2 tmproad, nx, ny
    
    plreader.init tmpfillet
    filletsplit = plreader.getLongDDLine(nx, ny)
    'ThisDrawing.ModelSpace.AddLightWeightPolyline filletsplit
    
    plreader.init tmproad
    roadsplit = plreader.getLongDDLine(nx, ny)
    'ThisDrawing.ModelSpace.AddLightWeightPolyline oldroadsplit
    
    'addVertex newroad, nx, ny
    
    
    tmpfillet.Delete
    tmproad.Delete
    
    
    Debug.Print ""
    
    checkCrossPoint3Ex = roadsplit
    
End Function


Function checkCrossPoint4Ex(road As AcadEntity, roadsplit() As Double, np As clsPoint) As Double()


    Dim tmpfillet As AcadLWPolyline
    Dim tmproad As AcadLWPolyline
    Dim intersec As Variant
    
    Dim selidx As Integer
    Dim mindist As Double
    
    Dim plreader As New ClsPolylineReader
    
    Dim x, y As Double
    Dim nx As Double
    Dim ny As Double
    
    Dim b1, b2 As Boolean
    
    selidx = -1
    mindist = 99999
    
    Set tmpfillet = ThisDrawing.ModelSpace.AddLightWeightPolyline(filletsplit)
    Set tmproad = ThisDrawing.ModelSpace.AddLightWeightPolyline(roadsplit)
    
    intersec = searchCrossVertext(tmpfillet, road)
    
    'addDonut5 np.x, np.y
    
    For i = 0 To UBound(intersec) Step 3
    
        x = intersec(i)
        y = intersec(i + 1)
    
        'b1 = isContains(tmpfillet, CDbl(x), CDbl(y))
        'b2 = isContains(tmproad, CDbl(x), CDbl(y))
        
        
        dist = getDistance(np.x, np.y, intersec(i), intersec(i + 1))
            
        'addDonutA intersec(i), intersec(i + 1)
            
        If dist < mindist Then
            
            mindist = dist
            selidx = i
        End If
        
        
    Next i
    
    
    If selidx = -1 Then
        Return
    End If
    
    
    nx = intersec(selidx)
    ny = intersec(selidx + 1)
    
    addDonutA nx, ny
    
    np2.x = nx
    np2.y = ny
    
    
    
    addVertex tmpfillet, nx, ny
    addVertexT2 tmproad, nx, ny
    
    plreader.init tmpfillet
    filletsplit = plreader.getLongDDLine(nx, ny)
    'Set tmpf = ThisDrawing.ModelSpace.AddLightWeightPolyline(filletsplit)
    'tmpf.color = acBlue
    
    plreader.init tmproad
    roadsplit = plreader.getLongDDLine(nx, ny)
    'Set tmpf = ThisDrawing.ModelSpace.AddLightWeightPolyline(oldroadsplit)
    'tmpf.color = acRed
    
    'addVertex newroad, nx, ny
    
    
    tmpfillet.Delete
    tmproad.Delete
    
    
    Debug.Print ""
    
    checkCrossPoint4Ex = roadsplit
    
End Function

Attribute VB_Name = "clsPoint"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Public x As Double
Public y As Double

Public Function initXy(ByVal xx As Double, ByVal yy As Double)
    x = xx
    y = yy
End Function

Public Function initPt(pt As Variant)
    x = pt(0)
    y = pt(1)
End Function


Public Function distance(pt As clsPoint) As Double
 
    Dim ret As Double
    
 
    ret = Sqr((pt.x - x) * (pt.x - x) + (pt.y - y) * (pt.y - y))

    distance = ret

End Function

Public Function getPoints() As Double()

    Dim pt(0 To 1) As Double
    
    
    pt(0) = x
    pt(1) = y
    
    getPoints = pt
    

End Function

Public Function isEquals(p As clsPoint) As Boolean


    If Int(x * P2P_TOL) = Int(p.x * P2P_TOL) And Int(y * P2P_TOL) = Int(p.y * P2P_TOL) Then
        isEquals = True
        
    Else
        isEquals = False
    End If


End Function

Attribute VB_Name = "clsPolygonReader"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private ent As AcadEntity
Private index As Integer    '현재위치
Private coord() As Double
Private size As Integer '포인트 크기(/3 - x,y,z)
Private sidx As Integer '시작지점
Private reverse As Boolean
Private eidx As Integer



Private pts As New clsPoint
Private pte As New clsPoint

Const C_ST = 2

Public Function init(e As AcadEntity)
    Set ent = e
    
    coord = ent.Coordinates
    size = UBound(coord)
    
    reverse = False
End Function


Public Function setReverse()

    If reverse = True Then
        reverse = False
    Else
        reverse = True
    End If

End Function

Public Function getSize()

    
    getSize = size

End Function


Public Function setIndex(i As Integer)

    index = i

End Function

Public Function setEIndexByPoint(e As clsPoint)

    eidx = getIndexByPoint(e)
    
    pte.x = e.x
    pte.y = e.y
    
End Function


Public Function setIndexByPoint(p As clsPoint)
    
    sidx = getIndexByPoint(p)
    
    pts.x = p.x
    pts.y = p.y
    

End Function

Public Function getSIndex() As Integer
    getSIndex = sidx
End Function




Public Function getIndexByPoint(p As clsPoint) As Integer

    Dim idx As Integer
    
    idx = -1


    Debug.Print "BSE: " & p.x & p.y & "==========="
    

    For i = 0 To size Step C_ST
    
        x = coord(i)
        y = coord(i + 1)
        
        'Debug.Print "idx: " & i & " > "  & x & y & "===="
        
        If Int(p.x * P2P_TOL) = Int(x * P2P_TOL) And Int(p.y * P2P_TOL) = Int(y * P2P_TOL) Then
            idx = i
            getIndexByPoint = idx
            Debug.Print "--> INDEX FOUND idx: " & i & " > " & x & y & "===="
            Exit Function
        End If
    
    Next i
    
    
    Debug.Print "result: getIndexByPoint: " & idx
    
    If idx = -1 Then
            Debug.Print "getIndexByPoint: " & idx
    End If
    

End Function





Public Function checkDirection(p As clsPoint)

    Dim cp As New clsPoint
    Dim np As New clsPoint
    Dim angle As Double
    Dim lp As Boolean
    
    lp = True
    reverse = False
    setIndex sidx
    Set cp = getPoint(sidx)
    
    'Do While lp
    '    Set np = nextPoint
    '    If cp.x = np.x And cp.y = np.y Then
    '        lp = False
    '    End If
    'Loop
    
    
        
    
    
    'addDonut9 cp.x, cp.y
    'addDonut9 np.x, np.y
    'addDonut9 p.x, p.y
    

    'd1 = getDistance(cp.x, cp.y, p.x, p.y)
    'd2 = getDistance(np.x, np.y, p.x, p.y)

    'If d1 < d2 Then
    '    reverse = True
    'End If
    angle = getAngleEx(cp.x, cp.y, np.x, np.y, p.x, p.y)
    
    
    Debug.Print "angle: " & angle
    
    If angle < 0 And Abs(angle) > PI Then
        angle = 2 * PI + angle
    End If
    
    'addDonut5 np.x, np.y
    
    If Abs(angle) > PI_2 Then
        reverse = True
    End If
    
    Debug.Print "angle: " & angle & ", reverse: " & reverse
    
    



End Function


Public Function getCurrentPoint() As clsPoint

    Dim p As New clsPoint
    
    p.x = coord(index)
    p.y = coord(index + 1)
    
    
    Set getCurrentPoint = p

End Function

Public Function nextPoint() As clsPoint
    Dim p As New clsPoint
    
    
    If reverse = False Then
        index = index + C_ST
    
        If index > size Then
            index = 0
        End If
    Else
        index = index - C_ST
    
        If index < 0 Then
        index = size - C_ST + 1
        End If
    
    End If
    
    
    p.x = coord(index)
    p.y = coord(index + 1)
    
    
    Set nextPoint = p
End Function


Public Function nextPointHalf() As clsPoint
    Dim p As New clsPoint
    
    
    If reverse = False Then
        index = index + C_ST
    
        If index > size Then
            index = -1
        End If
    Else
        index = index - C_ST
    
        If index < 0 Then
            index = -1
        End If
    
    End If
    
    
    If index > 0 Then
        p.x = coord(index)
        p.y = coord(index + 1)
    
    End If
    
    Set nextPointHalf = p
End Function


Public Function prevPoint() As clsPoint
    Dim p As New clsPoint
    
    If reverse = False Then
        index = index - C_ST
        
        If index < 0 Then
            index = size - C_ST + 1
        End If
    Else
        index = index + C_ST
    
        If index > size Then
            index = 0
        End If
    End If
    
    
    p.x = coord(index)
    p.y = coord(index + 1)
    
    Set prevPoint = p
End Function


Public Function getPoint(idx As Integer) As clsPoint
    Dim p As New clsPoint
    
    p.x = coord(idx)
    p.y = coord(idx + 1)
    
    Set getPoint = p
End Function



Public Function splitInnerLine(startp As clsPoint, endp As clsPoint) As Double()

    Dim p As New clsPoint
    Dim np As New clsPoint
    Dim count As Integer
    Dim ret() As Double
    Dim idx As Integer

    setIndexByPoint startp
    setIndex (sidx)
    
    Set p = getPoint(sidx)
    Set np = nextPoint()
    
    count = 1
    
    Do While (np.isEquals(endp) = False And size > count)
        count = count + 1
        Set np = nextPoint()
        
    Loop
    
    
    idx = 0
    ReDim ret(0 To count * 2 + 1) As Double
    
    setIndexByPoint startp
    setIndex (sidx)
    
    Set p = getPoint(sidx)
    
    ret(idx) = p.x
    idx = idx + 1
    ret(idx) = p.y
    idx = idx + 1
    
    'addDonut5 p.x, p.y
    
    Set np = nextPoint()
    
    ret(idx) = np.x
    idx = idx + 1
    ret(idx) = np.y
    idx = idx + 1
    
    'addDonut5 p.x, p.y
    
    count = 1
    
    Do While (np.isEquals(endp) = False And size > count)
        count = count + 1
        Set np = nextPoint()
        ret(idx) = np.x
        idx = idx + 1
        ret(idx) = np.y
        idx = idx + 1
    Loop
    
    splitInnerLine = ret
    
End Function


Public Function splitOutLine(startp As clsPoint, endp As clsPoint) As Double()

    Dim p As New clsPoint
    Dim np As New clsPoint
    Dim count As Integer
    Dim ret() As Double
    Dim idx As Integer

    setIndexByPoint startp
    setIndex (sidx)
    
    Set p = getPoint(sidx)
    Set np = nextPoint()
    
    count = 1
    
    Do While (np.isEquals(endp) = False And size > count)
        count = count + 1
        Set np = nextPoint()
        
    Loop
    
    
    idx = 0
    ReDim ret(0 To count * 2 + 1) As Double
    
    setIndexByPoint startp
    setIndex (sidx)
    
    Set p = getPoint(sidx)
    
    ret(idx) = p.x
    idx = idx + 1
    ret(idx) = p.y
    idx = idx + 1
    
    Set np = nextPoint()
    
    ret(idx) = np.x
    idx = idx + 1
    ret(idx) = np.y
    idx = idx + 1
    
    count = 1
    
    Do While (np.isEquals(endp) = False And size > count)
        count = count + 1
        Set np = nextPoint()
        ret(idx) = np.x
        idx = idx + 1
        ret(idx) = np.y
        idx = idx + 1
    Loop
    
    splitInnerLine = ret
    
End Function



Public Function getLine(pt As clsPoint) As AcadLine

    Dim newp As AcadLine


    
    idx = getIndexByPoint(pt)
    setIndex (idx)
    
    
    Set newp = getLineByEntity(ent, pt.x, pt.y)
     
    
    Set getLine = newp
    

End Function




Function getShortLine2() As Double()    'Closed일때만 사용가능

    Dim line1 As AcadLWPolyline
    Dim line2 As AcadLWPolyline
    Dim ddd() As Double
    
    setIndex sidx
    Set line1 = getLine1
    
    setIndex sidx
    setReverse
    Set line2 = getLine1
    
    
    len1 = getLWPDistance(line1)
    len2 = getLWPDistance(line2)
    
    
    If len1 < len2 Then
        'LINE 1
        line2.Delete
        setReverse
    Else
        'LINE 2
        line1.Delete
        Set line1 = line2
    End If
    
     
    ddd = line1.Coordinates

    line1.Delete
    

    getShortLine2 = ddd
    
End Function

Function getShortLine2Half() As Double()

    Dim line1 As AcadLWPolyline
    Dim line2 As AcadLWPolyline
    Dim ddd() As Double
    Dim len1, len2 As Double
    
    setIndex sidx
    Set line1 = getLine1Half
    
    setIndex sidx
    setReverse
    Set line2 = getLine1Half
    
    If line1 Is Nothing = True Then
        len1 = 99999
    Else
        len1 = getLWPDistance(line1)
    End If
    
    If line2 Is Nothing = True Then
        len2 = 99999
    Else
        len2 = getLWPDistance(line2)
    End If
    
    
    If len1 < len2 Then
        'LINE 1
        
        If line2 Is Nothing = False Then
            line2.Delete
        End If
        setReverse
    Else
        'LINE 2
        If line1 Is Nothing = False Then
            line1.Delete
        End If
        Set line1 = line2
    End If
    
     
    ddd = line1.Coordinates

    line1.Delete
    

    getShortLine2Half = ddd
    
End Function


Function getLongLine2() As Double()

    Dim line1 As AcadLWPolyline
    Dim line2 As AcadLWPolyline
    Dim ddd() As Double
    Dim ret() As Double
    
    setIndex sidx
    Set line1 = getLine1
    
    setIndex sidx
    setReverse
    Set line2 = getLine1
    
    
    len1 = getLWPDistance(line1)
    len2 = getLWPDistance(line2)
    
    
    If len1 > len2 Then
        'LINE 1
        line2.Delete
        setReverse
    Else
        'LINE 2
        line1.Delete
        Set line1 = line2
    End If
    
     
    ddd = line1.Coordinates
    
     
    ret = checkDirection2(ddd)

    line1.Delete

    getLongLine2 = ret
    
End Function


Function checkDirection2(src() As Double) As Double()


    Dim ret() As Double

    count = UBound(src)
    d1 = getDistance(src(0), src(1), pts.x, pts.y)
    d2 = getDistance(src(count - 1), src(count), pts.x, pts.y)


    If d1 < d2 Then
    
        ReDim ret(0 To count) As Double
        
        For i = 0 To count Step 2
        
            ret(i) = src(count - i - 1)
            ret(i + 1) = src(count - i)
        
        Next
        
        checkDirection2 = ret
    Else
        checkDirection2 = src
    
    End If
    
    
    
    
    
    

End Function




Public Function getLWPDistance(ent As AcadLWPolyline) As Double


    Dim ddd() As Double
    Dim size As Integer
    Dim x1, y1, x2, y2 As Double
    Dim sum As Double
    
    sum = 0
    ddd = ent.Coordinates
    
    size = UBound(ddd)
    
    
    x1 = ddd(0)
    y1 = ddd(1)
    
    For i = 2 To size Step 2
    
        x2 = ddd(i)
        y2 = ddd(i + 1)
        
        sum = sum + getDistance(x1, y1, x2, y2)
        
        x1 = x2
        y1 = y2
    
    
    Next

    getLWPDistance = sum


End Function

Function getLine1() As AcadLWPolyline

    Dim pline As AcadLWPolyline
    Dim ptc As New clsPoint
    Dim pt As New clsPoint
    Dim ddd() As Double
    Dim size As Integer
    Dim eidx2 As Integer
    
    eidx2 = -1
    size = getSize
    
    
    Set ptc = getPoint(sidx)
    'addDonutA pte.x, pte.y
        
    For idx = 0 To size
        Set pt = nextPoint
        
        'addDonut5 pt.x, pt.y
        
        dist = getDistance(pt.x, pt.y, pte.x, pte.y)
        'Debug.Print dist
        
        If pte.isEquals(pt) = True Then
            eidx2 = idx + 1
            Exit For
        End If
        
    Next
    
    ReDim ddd(0 To eidx2 * 2 + 1) As Double
        
    ddd(0) = ptc.x
    ddd(1) = ptc.y
    
    setIndex sidx
        
    For idx = 1 To eidx2
        Set pt = nextPoint
        ddd(idx * 2) = pt.x
        ddd(idx * 2 + 1) = pt.y
    Next
    
    Set getLine1 = ThisDrawing.ModelSpace.AddLightWeightPolyline(ddd)
    
    
    
End Function


Function getLine1Half() As AcadLWPolyline

    Dim pline As AcadLWPolyline
    Dim ptc As New clsPoint
    Dim pt As New clsPoint
    Dim ddd() As Double
    Dim size As Integer
    Dim eidx2 As Integer
    Dim ret As AcadEntity
    
    eidx2 = -1
    size = getSize
    
    
    Set ptc = getPoint(sidx)
    'addDonutA pte.x, pte.y
        
    For idx = 0 To size
        Set pt = nextPointHalf
        
        If pt.x = 0 And pt.y = 0 Then
        
            GoTo BrokenLine
        
        End If
        
        'addDonut5 pt.x, pt.y
        
        dist = getDistance(pt.x, pt.y, pte.x, pte.y)
        'Debug.Print dist
        
        If pte.isEquals(pt) = True Then
            eidx2 = idx + 1
            Exit For
        End If
        
    Next
    
    ReDim ddd(0 To eidx2 * 2 + 1) As Double
        
    ddd(0) = ptc.x
    ddd(1) = ptc.y
    
    setIndex sidx
        
    For idx = 1 To eidx2
        Set pt = nextPoint
        ddd(idx * 2) = pt.x
        ddd(idx * 2 + 1) = pt.y
    Next
    
    Set ret = ThisDrawing.ModelSpace.AddLightWeightPolyline(ddd)
    ret.color = acBlue
BrokenLine:
    Set getLine1Half = ret
    
End Function




Function getEdgeCollection() As Collection

    Dim col As New Collection
    Dim sp As New clsPoint
    Dim p1 As New clsPoint
    Dim cp As New clsPoint
    Dim p2 As New clsPoint
    Dim rad As Double
    Dim b_ortho As Boolean
    
    index = 0
    sidx = 0
    eidx = 0
    
    Set p1 = getCurrentPoint
    
    
    Set cp = nextPoint
    
    sp.x = cp.x
    sp.y = cp.y
    'p2.x = sp.x
    'p2.y = sp.y
    
    
    
    For i = 0 To size / 2
    
     
        
        Set p2 = nextPoint
        
        rad = getAngleEx(cp.x, cp.y, p1.x, p1.y, p2.x, p2.y)
        
        b_ortho = isLooseOrthogonalRadian(rad)
        
        If b_ortho = True Then
            'addDonutA cp.x, cp.y
            col.add cp.x
            col.add cp.y
        End If
        
        'Debug.Print "rad " & rad & " " & b_ortho
        
        p1.x = cp.x
        p1.y = cp.y
        cp.x = p2.x
        cp.y = p2.y
        
        
    
    Next i
     
     
    Set getEdgeCollection = col


End Function


Function findWeiredLine()

    Dim sp As New clsPoint
    Dim p1 As New clsPoint
    Dim cp As New clsPoint
    Dim p2 As New clsPoint
    Dim rad As Double
    Dim b_ortho As Boolean
    Dim insertionPoint(0 To 2) As Double
    Dim resent As AcadText
    Dim rad2 As Double
    
    Dim sus As Boolean
    
    
    index = 0
    sidx = 0
    eidx = 0
    
    Set p1 = getCurrentPoint
    
    
    Set cp = nextPoint
    
    sp.x = cp.x
    sp.y = cp.y
    'p2.x = sp.x
    'p2.y = sp.y
    
    susp = False
    
    For i = 0 To size / 2
    
     
        
        Set p2 = nextPoint
        
        rad = getAngleEx(cp.x, cp.y, p1.x, p1.y, p2.x, p2.y)
        
        'addDonut5 cp.x, cp.y
        
        rad2 = PI * 2 - Abs(rad)
        
        If Abs(rad) < 0.01 Or rad2 < 0.01 Then
        
            susp = True
        
            If susp = True Then
        
                addDonutA cp.x, cp.y
                
                insertionPoint(0) = cp.x
                insertionPoint(1) = cp.y
                insertionPoint(2) = 0
                ThisDrawing.ModelSpace.AddText "Error", insertionPoint, 10
                susp = False
            Else
            
                susp = True
            End If
            
        Else
            susp = False
            
        End If
        
        Debug.Print "rad " & Abs(rad) & " " & b_ortho
        
        
        p1.x = cp.x
        p1.y = cp.y
        cp.x = p2.x
        cp.y = p2.y
        
        
    Next i
     
     
     


End Function

Attribute VB_Name = "clsSelSets"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Const VK_ESCAPE = &H1B, VK_ENTER = &HD, VK_LBUTTON = &H1


Public Function selectArc()
    Dim UsersSelection As AcadSelectionSet
    Dim FilterType(0) As Integer
    Dim FilterData(0) As Variant
    Dim arcObjs As AcadEntity
    Dim count As Integer
    Dim sss As Variant
    
 
    On Error GoTo errControl
    
start:
 
     With ThisDrawing
        On Error Resume Next
        .SelectionSets("CurrentSelection").Delete
        Set UsersSelection = .SelectionSets.add("CurrentSelection")
        
        FilterType(0) = 0
        FilterData(0) = "Arc"
        
        UsersSelection.SelectOnScreen FilterType, FilterData
        
        
        count = getEntitySize(UsersSelection, "AcDbArc")
            
        If count = 0 Then
            Resume
        End If
        
        For i = 0 To count
            Set arcObjs = UsersSelection.Item(i)
            Exit For
        Next i
    End With
    
    
errControl:
    
    Debug.Print Err.Description
    
    If Err.Description = "Invalid argument index in Item" Then
    
        If CheckKey(VK_ESCAPE) = True Or CheckKey(VK_ENTER) Then
            Debug.Print "End"
        
            End
        Else
            Debug.Print "Resume"
            Resume
        End If
    ElseIf Err.Description = "Key not found" Then
    
    
    End If
    
    
    
    
    
    Set selectArc = arcObjs
End Function


Public Function selectLine()
    Dim UsersSelection As AcadSelectionSet
    Dim FilterType(0) As Integer
    Dim FilterData(0) As Variant
    Dim arcObjs As AcadEntity
    Dim count As Integer
    Dim sss As Variant
    
 
    On Error GoTo errControl
    
start:
 
     With ThisDrawing
        On Error Resume Next
        .SelectionSets("CurrentSelection").Delete
        Set UsersSelection = .SelectionSets.add("CurrentSelection")
        
        FilterType(0) = 0
        FilterData(0) = "Line"
        
        UsersSelection.SelectOnScreen FilterType, FilterData
        
        
        count = getEntitySize(UsersSelection, "AcLine")
            
        If count = 0 Then
            Resume
        End If
        
        For i = 0 To count
            Set arcObjs = UsersSelection.Item(i)
            Exit For
        Next i
    End With
    
    
errControl:
    
    Debug.Print Err.Description
    
    If Err.Description = "Invalid argument index in Item" Then
    
        If CheckKey(VK_ESCAPE) = True Or CheckKey(VK_ENTER) Then
            Debug.Print "End"
        
            End
        Else
            Debug.Print "Resume"
            Resume
        End If
    ElseIf Err.Description = "Key not found" Then
    
    
    End If
    
    
    
    
    
    Set selectLine = arcObjs
End Function


Public Function selectPolyline()
    Dim UsersSelection As AcadSelectionSet
    Dim FilterType(0) As Integer
    Dim FilterData(0) As Variant
    Dim arcObjs As AcadEntity
    Dim count As Integer
    Dim sss As Variant
    
 
    On Error GoTo errControl
    
start:
 
     With ThisDrawing
        On Error Resume Next
        .SelectionSets("CurrentSelection").Delete
        Set UsersSelection = .SelectionSets.add("CurrentSelection")
        
        FilterType(0) = 0
        FilterData(0) = "LWPolyline"
        
        UsersSelection.SelectOnScreen FilterType, FilterData
        
        
        count = getEntitySize(UsersSelection, "AcDbPolyline")
            
        If count = 0 Then
            Resume
        End If
        
        For i = 0 To count
            Set arcObjs = UsersSelection.Item(i)
            Exit For
        Next i
    End With
    
    
errControl:
    
    Debug.Print Err.Description
    
    If Err.Description = "Invalid argument index in Item" Then
    
        If CheckKey(VK_ESCAPE) = True Or CheckKey(VK_ENTER) Then
            Debug.Print "End"
        
            End
        Else
            Debug.Print "Resume"
            Resume
        End If
    ElseIf Err.Description = "Key not found" Then
    
    
    End If
    
    
    
    
    
    Set selectPolyline = arcObjs
End Function


Public Function selectOnePolyline()
    Dim UsersSelection As AcadSelectionSet
    Dim FilterType(0) As Integer
    Dim FilterData(0) As Variant
    Dim arcObjs As AcadEntity
    Dim count As Integer
    Dim sss As Variant
    
 
    On Error GoTo errControl
    
start:
 
     With ThisDrawing
        On Error Resume Next
        .SelectionSets("CurrentSelection").Delete
        Set UsersSelection = .SelectionSets.add("CurrentSelection")
        
        FilterType(0) = 0
        FilterData(0) = "LWPolyline"
        
        UsersSelection.SelectOnScreen FilterType, FilterData
        
        
        count = getEntitySize(UsersSelection, "AcDbPolyline")
            
        If count = 0 Then
            Resume
        End If
        
        If count > 1 Then
            GoTo errControl
        End If
        For i = 0 To count
            Set arcObjs = UsersSelection.Item(i)
            Exit For
        Next i
    End With
    
    
errControl:
    
    Debug.Print Err.Description
    
    If Err.Description = "Invalid argument index in Item" Then
    
        If CheckKey(VK_ESCAPE) = True Or CheckKey(VK_ENTER) Then
            Debug.Print "End"
        
            End
        Else
            Debug.Print "Resume"
            Resume
        End If
    ElseIf Err.Description = "Key not found" Then
    
    
    End If
    
    
    
    
    
    Set selectOnePolyline = arcObjs
End Function


Public Function selectOnePolylineEx()
    Dim UsersSelection As AcadSelectionSet
    Dim FilterType(0) As Integer
    Dim FilterData(0) As Variant
    Dim arcObj As AcadEntity
    Dim count As Integer
    Dim sss As Variant
    Dim pt() As Variant
    
    On Error GoTo errControl
    
start:
 
     With ThisDrawing
        On Error Resume Next
        .SelectionSets("CurrentSelection").Delete
        Set UsersSelection = .SelectionSets.add("CurrentSelection")
        
        UsersSelection.SelectAtPoint (pt)
     
        Set arcObj = UsersSelection.Item(0)
         
            
        If count = 0 Then
            Resume
        End If
        
        If count > 1 Then
            GoTo errControl
        End If
    End With
    
    
errControl:
    
    Debug.Print Err.Description
    
    If Err.Description = "Invalid argument index in Item" Then
    
        If CheckKey(VK_ESCAPE) = True Or CheckKey(VK_ENTER) Then
            Debug.Print "End"
        
            End
        Else
            Debug.Print "Resume"
            Resume
        End If
    ElseIf Err.Description = "Key not found" Then
    
    
    End If
    
    
    
    
    
    Set selectOnePolylineEx = arcObj
End Function




Public Function selectAnything()
    Dim UsersSelection As AcadSelectionSet
    Dim FilterType(0) As Integer
    Dim FilterData(0) As Variant
    Dim arcObjs As AcadEntity
    Dim count As Integer
    Dim sss As Variant
    
 
    On Error GoTo errControl
    
start:
 
     With ThisDrawing
        On Error Resume Next
        .SelectionSets("CurrentSelection").Delete
        Set UsersSelection = .SelectionSets.add("CurrentSelection")
        
        'FilterType(0) = 0
        'FilterData(0) = "LWPolyline"
        
        UsersSelection.SelectOnScreen 'FilterType, FilterData
        
        count = UsersSelection.count
            
        If count = 0 Then
            Resume
        End If
        
        For i = 0 To count
            Set arcObjs = UsersSelection.Item(i)
            Exit For
        Next i
    End With
    
    
errControl:
    
    Debug.Print Err.Description
    
    If Err.Description = "Invalid argument index in Item" Then
    
        If CheckKey(VK_ESCAPE) = True Or CheckKey(VK_ENTER) Then
            Debug.Print "End"
        
            End
        Else
            Debug.Print "Resume"
            Resume
        End If
    ElseIf Err.Description = "Key not found" Then
    
    
    End If
    
    
    Set selectAnything = arcObjs
End Function

Attribute VB_Name = "commonMondule"

Function IsArrayEmpty(ar As Variant) As Boolean
    If InStr(TypeName(ar), "(") > 0 Then
        If Not IsEmpty(ar) Then
            If UBound(ar) >= 0 Then
                IsArrayEmpty = False
            Else
                IsArrayEmpty = True
            End If
        End If
    End If
End Function

Attribute VB_Name = "filletModule"
Public Const PI As Double = 3.14159265358979
Public Const PI_2 As Double = 1.57079632679489







Function arc2line(myArc As AcadArc) As AcadEntity

    Dim retobj As AcadEntity
    Dim delta As Double
    Dim numOfSegments As Integer
    Dim points() As Double
    
    Dim tol As Double
    
    tol = getDefaultTolerance
    
    delta = myArc.EndAngle - myArc.StartAngle
    If delta < 0 Then delta = delta + (2 * PI)
    
    numOfSegments = CInt(myArc.ArcLength / tol)
    ReDim points(0 To 2 * numOfSegments + 1)
    ang = 1 / (myArc.Radius / tol)
    points(0) = myArc.startPoint(0)
    points(1) = myArc.startPoint(1)
    adir = ang
    For x = 2 To UBound(points) - 2 Step 2
        mypolarpoint = ThisDrawing.Utility.PolarPoint(myArc.Center, myArc.StartAngle + adir, myArc.Radius)
        adir = adir + ang
        points(x) = mypolarpoint(0)
        points(x + 1) = mypolarpoint(1)
    Next x
    points(UBound(points) - 1) = myArc.endPoint(0)
    points(UBound(points) - 0) = myArc.endPoint(1)
    Set retobj = ThisDrawing.ModelSpace.AddLightWeightPolyline(points)
    
    Set arc2line = retobj

End Function




Function cir2line(myCir As AcadCircle) As AcadEntity

    Dim retobj As AcadEntity
    Dim delta As Double
    Dim vv As Variant
    
    delta = 2 * PI
    
    Dim numOfSegments As Integer
    Dim points() As Double
    
    Dim tol As Double
    tol = getDefaultTolerance
    
    numOfSegments = CInt(PI * myCir.Diameter / tol)
    ReDim points(0 To 2 * numOfSegments + 1)
    ang = 2 * PI / numOfSegments
    adir = 0
    For x = 0 To UBound(points) - 2 Step 2
        mypolarpoint = ThisDrawing.Utility.PolarPoint(myCir.Center, adir, myCir.Radius)
        adir = adir + ang
        points(x) = mypolarpoint(0)
        points(x + 1) = mypolarpoint(1)
    Next x
    points(UBound(points) - 1) = points(0)
    points(UBound(points) - 0) = points(1)
    Set retobj = ThisDrawing.ModelSpace.AddLightWeightPolyline(points)
    retobj.Closed = True
    
    Set cir2line = retobj

End Function



Function addCrossVertext(src As AcadEntity, dst As AcadEntity) As Variant

    Dim ret As Variant
    Dim size As Integer
    
    ret = src.IntersectWith(dst, acExtendOtherEntity)   'find vertex
    size = 0
    
    
    size = UBound(ret)
    
    If size > 0 Then
        For i = 0 To size Step 3
            addDonut2 ret(i), ret(i + 1)
            
            addVertex dst, ret(i), ret(i + 1)     ' add vertext
        Next
    Else
    
    End If
    
    addCrossVertext = ret

End Function


Function findVertex(ent As AcadEntity, ent2 As AcadEntity) As Double()

    Dim ddd() As Double
    Dim filletpoint(0 To 7) As Double   '8
        
    ddd = ent2.Coordinates
    
    count = UBound(ddd)
    
    vx = ddd(count - 1)
    vy = ddd(count)
    
    newp = addVertex(ent, vx, vy)
    
    If newp(0) <> 0 And newp(1) <> 0 Then
    
        filletpoint(index) = newp(0)
        index = index + 1
        filletpoint(index) = newp(1)
        index = index + 1
         
    Else
        vx = ddd(0)
        vy = ddd(1)
        
        newp = addVertex(ent, vx, vy)
        
        If newp(0) <> 0 And newp(1) <> 0 Then
        
            filletpoint(index) = newp(0)
            index = index + 1
            filletpoint(index) = newp(1)
            index = index + 1
        End If
    End If
    
    findVertex = newp

End Function



Function getNearestVertex(ent2 As AcadEntity, ref As clsPoint) As Double()

    Dim ent2d() As Double
    Dim x1, y1, x2, y2 As Double
    
    Dim dist1, dist2 As Double
    Dim ret(0 To 1) As Double
    
    ent2d = ent2.Coordinates
    count = UBound(ent2d)
    
    
    x1 = ent2d(0)
    y1 = ent2d(1)
    
    x2 = ent2d(count - 1)
    y2 = ent2d(count)
    
    
    'addDonutA x1, y1
    'addDonutA x2, y2
        
    dist1 = getDistance(x1, y1, ref.x, ref.y)
    dist2 = getDistance(x2, y2, ref.x, ref.y)
    
    If dist1 > dist2 Then
        ret(0) = x2
        ret(1) = y2
    Else
        ret(0) = x1
        ret(1) = y1
    End If
    
    getNearestVertex = ret


End Function

Function findVertex2(ent As AcadEntity, ent2 As AcadEntity, pt As clsPoint) As Double()

    Dim filletpoint(0 To 7) As Double   '8
    Dim nv() As Double
    
    nv = getNearestVertex(ent2, pt)
    vx = nv(0)
    vy = nv(1)
    
    newp = addVertex2(ent, vx, vy)
    
    If newp(0) <> 0 And newp(1) <> 0 Then
    
        filletpoint(index) = newp(0)
        index = index + 1
        filletpoint(index) = newp(1)
        index = index + 1
   
    End If
    
    findVertex2 = newp

End Function


Function addVertex(ent As AcadEntity, ByVal vx As Double, ByVal vy As Double) As Double()

    Dim newv(0 To 1) As Double
    Dim ddd() As Double
    Dim count As Integer
    Dim distance As Double

    Dim ret As Boolean
    Dim newp() As Double
    
    Dim selidx As Integer
    Dim mindist As Double
    Dim exists As Boolean
    
    newv(0) = vx: newv(1) = vy
    ret = False
    
    
    exists = isContains(ent, vx, vy)
    
    If exists = False Then
        
        mindist = 999999
        
        'addDonutA vx, vy
        ddd = ent.Coordinates
        count = UBound(ddd)
        
        x1 = ddd(count - 1)
        y1 = ddd(count)
        
        For ii = 0 To count Step 2
        
            x2 = ddd(ii)
            y2 = ddd(ii + 1)
            
            f = getTan(x1, x2, y1, y2)
            f1 = getTan(x1, vx, y1, vy)
            f2 = getTan(vx, x2, vy, y2)
             
            fd = XYDistance(x1, y1, x2, y2)
            fd1 = XYDistance(x1, y1, vx, vy) + XYDistance(x2, y2, vx, vy)
            
            'addDonutA x2, y2
            'addDonut x1, y1
            
            
            If Abs(fd - fd1) < mindist Then
                mindist = Abs(fd - fd1)
                newp = crossXY(vx, vy, x1, y1, x2, y2)
                selidx = ii
            
            End If
            
            'If Abs(fd - fd1) < PD_TOL Then
                
                'addDonut x2, y2
                'addDonut x1, y1
                
                
            '    newp = crossXY(vx, vy, x1, y1, x2, y2)
                
                'addDonut vx, vy
                
            '    newv(0) = newp(0)
            '    newv(1) = newp(1)
            '    addDonut vx, vy
            '    ent.addVertex ii / 2, newv
            '    ent.Update
            '    ret = True
            '    Exit For
            
            'End If
            
            x1 = x2
            y1 = y2
            
        Next ii
        
        If mindist < PD_TOL Then
            newv(0) = newp(0)
            newv(1) = newp(1)
            'addDonutA vx, vy
            ent.addVertex selidx / 2, newv
            ent.Update
            ret = True
        End If
        
        If ret = False Then
            newv(0) = 0
            newv(1) = 0
            Debug.Print "================NOT FOUND================"
        End If
    End If
    
    addVertex = newv
        
        
    
End Function

Function addVertexH(ent As AcadEntity, ByVal vx As Double, ByVal vy As Double) As Double()

    Dim newv(0 To 1) As Double
    Dim ddd() As Double
    Dim count As Integer
    Dim distance As Double

    Dim ret As Boolean
    Dim newp() As Double
    
    Dim selidx As Integer
    Dim mindist As Double
    Dim exists As Boolean
    
    newv(0) = vx: newv(1) = vy
    ret = False
    
    
    exists = isContains(ent, vx, vy)
    
    If exists = False Then
        
        mindist = 999999
        
        'addDonutA vx, vy
        ddd = ent.Coordinates
        count = UBound(ddd)
        
        x1 = ddd(0)
        y1 = ddd(1)
        
        For ii = 2 To count Step 2
        
            x2 = ddd(ii)
            y2 = ddd(ii + 1)
            
            f = getTan(x1, x2, y1, y2)
            f1 = getTan(x1, vx, y1, vy)
            f2 = getTan(vx, x2, vy, y2)
             
            fd = XYDistance(x1, y1, x2, y2)
            fd1 = XYDistance(x1, y1, vx, vy) + XYDistance(x2, y2, vx, vy)
            
            'addDonutA x2, y2
            'addDonut5 x1, y1
            
            
            If Abs(fd - fd1) < mindist Then
                mindist = Abs(fd - fd1)
                newp = crossXY(vx, vy, x1, y1, x2, y2)
                selidx = ii
            
            End If
             
            x1 = x2
            y1 = y2
            
        Next ii
        
        selidx = selidx / 2
        
        If selidx = 0 Then
            selidx = 1
        End If
        
        If mindist < PD_TOL Then
            newv(0) = newp(0)
            newv(1) = newp(1)
            'addDonut5 newv(0), newv(1)
            
            'For ii = 0 To count Step 2
            '    x2 = ddd(ii)
            '    y2 = ddd(ii + 1)
            '    addDonutA x2, y2
            '    Debug.Print ""
            'Next ii
            
            ent.addVertex selidx, newv
            
            ent.Update
            ret = True
        End If
        
        If ret = False Then
            newv(0) = 0
            newv(1) = 0
            Debug.Print "================NOT FOUND================"
        End If
    End If
    
    addVertexH = newv
        
End Function

Function addVertexT(ent As AcadEntity, ByVal vx As Double, ByVal vy As Double) As Double()

    Dim newv(0 To 1) As Double
    Dim ddd() As Double
    Dim count As Integer
    Dim distance As Double

    Dim ret As Boolean
    Dim newp() As Double
    
    Dim selidx As Integer
    Dim mindist As Double
    Dim exists As Boolean
    
    newv(0) = vx: newv(1) = vy
    ret = False
    
    
    exists = isContains(ent, vx, vy)
    
    If exists = False Then
        
        mindist = 999999
        
        addDonutA vx, vy
        ddd = ent.Coordinates
        count = UBound(ddd)
        
        x1 = ddd(count - 1)
        y1 = ddd(count)
        
        For ii = 0 To count Step 2
        
            x2 = ddd(ii)
            y2 = ddd(ii + 1)
            
            f = getTan(x1, x2, y1, y2)
            f1 = getTan(x1, vx, y1, vy)
            f2 = getTan(vx, x2, vy, y2)
             
            fd = XYDistance(x1, y1, x2, y2)
            fd1 = XYDistance(x1, y1, vx, vy) + XYDistance(x2, y2, vx, vy)
            
            addDonutA x2, y2
            addDonut5 x1, y1
            
            
            If Abs(fd - fd1) < mindist Then
                mindist = Abs(fd - fd1)
                newp = crossXY(vx, vy, x1, y1, x2, y2)
                selidx = ii
            
            End If
             
            x1 = x2
            y1 = y2
            
        Next ii
        
        If mindist < PD_TOL Then
            newv(0) = newp(0)
            newv(1) = newp(1)
            addDonutA vx, vy
            ent.addVertex selidx / 2, newv
            ent.Update
            ret = True
        End If
        
        If ret = False Then
            newv(0) = 0
            newv(1) = 0
            Debug.Print "================NOT FOUND================"
        End If
    End If
    
    addVertexT = newv
        
End Function


Function addVertexT2(ent As AcadEntity, ByVal vx As Double, ByVal vy As Double) As Double()

    Dim newv(0 To 1) As Double
    Dim ddd() As Double
    Dim count As Integer
    Dim distance As Double

    Dim ret As Boolean
    Dim newp() As Double
    
    Dim selidx As Integer
    Dim mindist As Double
    Dim exists As Boolean
    
    newv(0) = vx: newv(1) = vy
    ret = False
    
    
    exists = isContains(ent, vx, vy)
    
    If exists = False Then
        
        mindist = 999999
        
        addDonutA vx, vy
        ddd = ent.Coordinates
        count = UBound(ddd)
        
        x1 = ddd(count - 1)
        y1 = ddd(count)
        
        For ii = 0 To count Step 2
        
            x2 = ddd(ii)
            y2 = ddd(ii + 1)
            
            f = getTan(x1, x2, y1, y2)
            f1 = getTan(x1, vx, y1, vy)
            f2 = getTan(vx, x2, vy, y2)
             
            fd = XYDistance(x1, y1, x2, y2)
            fd1 = XYDistance(x1, y1, vx, vy) + XYDistance(x2, y2, vx, vy)
            
            addDonutA x2, y2
            addDonut5 x1, y1
            
            
            If Abs(fd - fd1) < mindist Then
                mindist = Abs(fd - fd1)
                newp = crossXY(vx, vy, x1, y1, x2, y2)
                selidx = ii
            
            End If
            
            'If Abs(fd - fd1) < PD_TOL Then
                
                'addDonut x2, y2
                'addDonut x1, y1
                
                
            '    newp = crossXY(vx, vy, x1, y1, x2, y2)
                
                'addDonut vx, vy
                
            '    newv(0) = newp(0)
            '    newv(1) = newp(1)
            '    addDonut vx, vy
            '    ent.addVertex ii / 2, newv
            '    ent.Update
            '    ret = True
            '    Exit For
            
            'End If
            
            x1 = x2
            y1 = y2
            
        Next ii
        
        If mindist < PD_TOL Then
            newv(0) = newp(0)
            newv(1) = newp(1)
            addDonutA vx, vy
            ent.addVertex selidx / 2, newv
            ent.Update
            ret = True
        End If
        
        If ret = False Then
            newv(0) = 0
            newv(1) = 0
            Debug.Print "================NOT FOUND================"
        End If
    End If
    
    addVertexT2 = newv
        
        
    
End Function

Function addVertex2(ent As AcadEntity, ByVal vx As Double, ByVal vy As Double) As Double()

    Dim newv(0 To 1) As Double
    Dim ddd() As Double
    Dim count As Integer
    Dim distance As Double

    Dim ret As Boolean
    Dim newp() As Double
    
    Dim mindist As Double
    Dim exists As Boolean
    mindist = 999999
    
    newv(0) = vx: newv(1) = vy
    ret = False
    
    
    exists = isContains(ent, vx, vy)
    If exists = False Then
        'addDonutA vx, vy
        ddd = ent.Coordinates
        count = UBound(ddd)
        
        x1 = ddd(count - 1)
        y1 = ddd(count)
        
        
        
        
        For ii = 0 To count Step 2
        
            x2 = ddd(ii)
            y2 = ddd(ii + 1)
            
            addDonutY x2, y2
            addDonutY x1, y1
            
            f = getTan(x1, x2, y1, y2)
            f1 = getTan(x1, vx, y1, vy)
            f2 = getTan(vx, x2, vy, y2)
             
            fd = XYDistance(x1, y1, x2, y2)
            fd1 = XYDistance(x1, y1, vx, vy) + XYDistance(x2, y2, vx, vy)
            
            
            If Abs(fd - fd1) < mindist Then
                mindist = Abs(fd - fd1)
                xx1 = x1
                yy1 = y1
                xx2 = x2
                yy2 = y2
                iii = ii
            End If
            
            x1 = x2
            y1 = y2
            
        Next ii
        
        
        Debug.Print "===========================>>>> " & mindist & ", " & PD_TOL
        
        
                
            'addDonut x2, y2
            'addDonut x1, y1
            
            
        newp = crossXY(vx, vy, xx1, yy1, xx2, yy2)
        
        'addDonut vx, vy
        
        newv(0) = newp(0)
        newv(1) = newp(1)
        'addDonutA vx, vy
        ent.addVertex iii / 2, newv
        ent.Update
        ret = True
            
        
        
        
        If ret = False Then
            newv(0) = 0
            newv(1) = 0
            Debug.Print "================NOT FOUND================"
        End If
    End If
    
    addVertex2 = newv
        
        
    
End Function


Function getTan(ByVal x1 As Double, ByVal x2 As Double, ByVal y1 As Double, ByVal y2 As Double) As Double
    
    Dim t As Double
    
    If x1 = x2 Then
    
        t = 1.79769313486232E+307
    Else
        t = (y2 - y1) / (x2 - x1)
    
    End If
    
    getTan = t

End Function






Function XYDistance(ByVal x1 As Double, ByVal y1 As Double, ByVal x2 As Double, ByVal y2 As Double) As Double
    Dim dblDist As Double
    Dim dblXSl As Double
    Dim dblYSl As Double

    Dim varErr As Variant
    On Error GoTo Err_Control

    dblXSl = (x1 - x2) ^ 2
    dblYSl = (y1 - y2) ^ 2
    dblDist = Sqr(dblXSl + dblYSl)

    XYDistance = dblDist

Exit_Here:
    Exit Function

Err_Control:

  Select Case Err.Number

  'Add additional Case selections here

    Case Else

    MsgBox Err.Description

    Err.Clear

    Resume Exit_Here

  End Select

End Function

Attribute VB_Name = "frmSettings"
Attribute VB_Base = "0{2525F3A6-B242-4515-B559-F32C66009DCB}{1E6162CB-AC6E-4851-AB04-D37BF3C68E38}"
Attribute VB_GlobalNameSpace = False
Attribute VB_Creatable = False
Attribute VB_PredeclaredId = True
Attribute VB_Exposed = False
Attribute VB_TemplateDerived = False
Attribute VB_Customizable = False
Private Sub frmSettings_Initialize()


    Debug.Print ""

End Sub


Public Sub frmSettings_init()
    
    
    tbChamferDist.Text = getDefaultChamferDistance
    tbFilletTol.Text = getDefaultTolerance
    tbFilletRad.Text = getDefaultFilletRadius
    tbFarDist.Text = getDefaultFarDistance
    tbLayerOn.Text = getDefaultLayerOnString
    
    
End Sub

Private Sub btnCancel_Click()

    
    Unload Me
End Sub

Private Sub btnOk_Click()


    Dim v As Variant

    v = tbFilletRad.Text

    setDefaultTolerance CDbl(tbFilletTol.Text)
    setDefaultFilletRadius CDbl(tbFilletRad.Text)
    setDefaultChamferDistance CDbl(tbChamferDist.Text)
    setDefaultFarDistance CInt(tbFarDist.Text)
    setDefaultLayerOn tbLayerOn.Text
    
    Unload Me
End Sub

Private Sub Label1_Click()

End Sub

Private Sub Label2_Click()

End Sub

Private Sub lblFilletTol_Click()

End Sub

Private Sub lblVer_Click()

End Sub

Private Sub TextBox1_Change()

End Sub

Private Sub tbFarDist_Change()

End Sub

Private Sub tbLayerOn_Change()

End Sub

Private Sub UserForm_Click()

End Sub

Attribute VB_Name = "layerModule"


Function newLayer(name As String)

    Dim lyr As AcadLayer
    Dim exist As Boolean
    Dim lname As String
    Dim idx As Integer

    exist = False
    count = ThisDrawing.layers.count
    
    For idx = 0 To count - 1
    
        lname = ThisDrawing.layers.Item(idx).name
        
        If lname = name Then
            exist = True
            Exit For
        End If
        
        
    Next idx
    
    
    If exist = False Then
    
        Set lyr = ThisDrawing.layers.add(name)
    End If
    

End Function


Function newFreezeLayer(name As String)

    Dim lyr As AcadLayer
    Dim exist As Boolean
    Dim lname As String
    Dim idx As Integer

    exist = False
    count = ThisDrawing.layers.count
    
    For idx = 0 To count - 1
    
        Set lyr = ThisDrawing.layers.Item(idx)
        lname = lyr.name
        
        If lname = name Then
            exist = True
            lyr.Freeze = True
            Exit For
        End If
        
        
    Next idx
    
    
    If exist = False Then
    
        Set lyr = ThisDrawing.layers.add(name)
        lyr.Freeze = True
    End If
    

End Function


Function getAddLayerName(name As String) As String

    Dim newname As String
    
    If name Like LYR_ADD & "*" Then
        newname = name
    Else
        newname = LYR_ADD & name
    End If
    
    newLayer newname
    getAddLayerName = newname

End Function

Function getDelLayerName(name As String) As String

    Dim newname As String
    
    If name Like LYR_DEL & "*" Then
        newname = name
    Else
        newname = LYR_DEL & name
    End If
    
    newLayer newname
    getDelLayerName = newname

End Function



Function showLayer(name As String)

    Dim lyr As AcadLayer
    Dim exist As Boolean
    Dim lname As String
    Dim idx As Integer

    exist = False
    count = ThisDrawing.layers.count
    
    For idx = 0 To count - 1
    
        lyr = ThisDrawing.layers.Item(idx)
        lname = lyr.name
        
        If lname = name Then
            lyr.LayerOn = True
            Exit For
        End If
        
        
    Next idx
    
End Function


Function showLayerLike(names() As String)

    Dim lyr As AcadLayer
    Dim exist As Boolean
    Dim lname As String
    Dim idx As Integer
    Dim name As String

    exist = False
    count = ThisDrawing.layers.count
    
    For idx = 0 To count - 1
    
        Set lyr = ThisDrawing.layers.Item(idx)
        lname = lyr.name
        
        For i = 0 To UBound(names)
            name = names(i)
            If lname Like name Then
                lyr.LayerOn = True
                Exit For
            End If
        
        Next
        
        
    Next idx
    
End Function



Function hideLayer(name As String)

    Dim lyr As AcadLayer
    Dim exist As Boolean
    Dim lname As String
    Dim idx As Integer

    exist = False
    count = ThisDrawing.layers.count
    
    For idx = 0 To count - 1
    
        lyr = ThisDrawing.layers.Item(idx)
        lname = lyr.name
        
        If lname = name Then
            lyr.LayerOn = False
            Exit For
        End If
        
        
    Next idx
    
End Function



Function hideLayerAll()

    Dim lyr As AcadLayer
    Dim idx As Integer

    count = ThisDrawing.layers.count
    
    For idx = 0 To count - 1
        Set lyr = ThisDrawing.layers.Item(idx)
        lyr.LayerOn = False
    Next idx
    
End Function

Function hideLayerLike(name As String)

    Dim lyr As AcadLayer
    Dim exist As Boolean
    Dim lname As String
    Dim idx As Integer

    exist = False
    count = ThisDrawing.layers.count
    
    For idx = 0 To count - 1
    
        lyr = ThisDrawing.layers.Item(idx)
        lname = lyr.name
        
        If lname Like name Then
            lyr.LayerOn = False
            Exit For
        End If
        
        
    Next idx
    
End Function



Function getLayers() As AcadLayer()

    Dim lyrs() As AcadLayer
    
    count = ThisDrawing.layers.count
    ReDim lyrs(0 To count)
    
    For i = 0 To count
    
        lyrs(i) = ThisDrawing.layers(i)
    
    Next
    
    
    getLayers = lyrs
    

End Function


Function getLayerByName(name As String) As AcadLayer

    Dim lyrs() As AcadLayer
    Dim lyr As AcadLayer
    
    On Error GoTo EndOfFunction
    
    count = ThisDrawing.layers.count
    ReDim lyrs(0 To count)
    
    For i = 0 To count
    
        Set lyrs(i) = ThisDrawing.layers(i)
        If lyrs(i).name = name Then
        
            Set lyr = lyrs(i)
            Exit For
        End If
        
    
    Next
    
EndOfFunction:
    
    Set getLayerByName = lyr
    

End Function


Function saveOnLayers()


    Dim str As String
    Dim lyr As AcadLayer
    Dim cnt As Integer
    
    
    str = ""
    count = ThisDrawing.layers.count
    ReDim lyrs(0 To count)
    
    For i = 0 To count - 1
    
        Set lyr = ThisDrawing.layers(i)
        
        If lyr.LayerOn = True Then
        
            If str = "" Then
            
                str = lyr.name
            
            Else
            
            str = str + "|" + lyr.name
            
            End If
        
            
        End If
    
    Next
    
    
    setTempSplit str
    
End Function


Function restoreOnLayers()


    Dim names() As String
    Dim name As String
    Dim lyr As AcadLayer
    Dim cnt As Integer
    
    
    count = ThisDrawing.layers.count
    
    names = getTempSplit
    
    For i = 0 To count - 1
    
        Set lyr = ThisDrawing.layers(i)
        
        For j = 0 To UBound(names)
        
            name = names(j)
        
            If name = lyr.name Then
            
                lyr.LayerOn = True
            End If
        Next j
            
         
    
    Next
    
    
    setTempSplit ""
    
End Function


Function deleteLayer(lyr As String)
   
    Dim ent As AcadEntity
    Dim oLayer As AcadLayer
       
    Set oLayer = getLayerByName(lyr)
    If oLayer Is Nothing = False Then
            
        For Each ent In ThisDrawing.ModelSpace
            If ent.layer = lyr Then
                ent.Delete
            End If
            
        Next
        
        oLayer.Delete
        
        ThisDrawing.Regen acActiveViewport
    End If
   
End Function





Function splitLastString(strInput As String, filter As String) As String
    Dim iSplit As Integer
    Dim strName As String
    Dim strLast As String
    Dim code As Variant
    
    On Error GoTo noneCode
    
    iSplit = InStrRev(strInput, filter)
    strName = Left(strInput, iSplit - 1)
    strLast = mid(strInput, iSplit + 1)
    
    code = CLng(strLast)
    
    splitLastString = strName
    Exit Function
    
noneCode:
    
    splitLastString = strInput
End Function
 

Function selectObjectFromLayer(lyrname As String) As AcadEntity


    Dim polylines As AcadSelectionSet
    Dim FilterType(0) As Integer
    Dim FilterData(0) As Variant
    Dim pl As AcadEntity
    
    On Error Resume Next
    
    Set polylines = ThisDrawing.SelectionSets.add("selections")
    
    If Err.Number <> 0 Then
        ThisDrawing.SelectionSets.Item("selections").Delete
        Set polylines = ThisDrawing.SelectionSets.add("selections")
    End If
    
    FilterType(0) = 8
    FilterData(0) = lyrname
    
    polylines.Select acSelectionSetAll, , , FilterType, FilterData
    
    Debug.Print lyrname & " object size: "; polylines.count
    
    If polylines.count > 0 Then
        Set pl = polylines.Item(0)
    End If
    
    Set selectObjectFromLayer = pl
    
End Function

Function selectObjectFromLayers(lyrname As String) As AcadEntity()


    Dim polylines As AcadSelectionSet
    Dim FilterType(0) As Integer
    Dim FilterData(0) As Variant
    Dim ents() As AcadEntity
    
    On Error Resume Next
    
    Set polylines = ThisDrawing.SelectionSets.add("selections")
    
    If Err.Number <> 0 Then
        ThisDrawing.SelectionSets.Item("selections").Delete
        Set polylines = ThisDrawing.SelectionSets.add("selections")
    End If
    
    FilterType(0) = 8
    FilterData(0) = lyrname
    
    polylines.Select acSelectionSetAll, , , FilterType, FilterData
    
    Debug.Print lyrname & " object size: "; polylines.count
    
    ReDim ents(polylines.count)
    
    For i = 0 To polylines.count
        Set ents(i) = polylines.Item(i)
    Next
    
    selectObjectFromLayers = ents
    
End Function

Attribute VB_Name = "polyline"
Function setWidth(ent As AcadLWPolyline, sw As Double, ew As Double)
    
    Dim ddd() As Double
    Dim cnt As Integer
    
    ddd = ent.Coordinates
    cnt = UBound(ddd)
    
    For i = 0 To cnt / 2
    
        ent.setWidth i, sw, ew
    
    Next i


End Function

Attribute VB_Name = "selector"

Const VK_ESCAPE = &H1B, VK_ENTER = &HD, VK_LBUTTON = &H1
Declare PtrSafe Function GetAsyncKeyState Lib "user32" (ByVal vKey As Long) As Integer


Function CheckKey(lngKey As Long) As Boolean
    If GetAsyncKeyState(lngKey) Then
        CheckKey = True
        Debug.Print "True"
        
    Else
        CheckKey = False
        Debug.Print "False"
    End If
End Function


Function selectArcObs() As AcadEntity()
    Dim UsersSelection As AcadSelectionSet
    Dim FilterType(0) As Integer
    Dim FilterData(0) As Variant
    Dim arcObjs() As AcadEntity
 
     With ThisDrawing
        On Error Resume Next
        
        .SelectionSets("CurrentSelection").Delete
        Set UsersSelection = .SelectionSets.add("CurrentSelection")
        
        FilterType(0) = 0
        FilterData(0) = "Arc"
        
        UsersSelection.SelectOnScreen FilterType, FilterData
        
        
        count = getEntitySize(UsersSelection, "AcDbArc")
        
        ReDim arcObjs(0 To count - 1) As AcadEntity
        
        For i = 0 To count
            Set arcObjs(i) = UsersSelection.Item(i)
        Next i
        
        
    End With
    
    selectArcObs = arcObjs

End Function



Function selectArcObj() As AcadEntity
    Dim UsersSelection As AcadSelectionSet
    Dim FilterType(0) As Integer
    Dim FilterData(0) As Variant
    Dim arcObjs As AcadEntity
    Dim count As Integer
 
     With ThisDrawing
        On Error Resume Next
        
        .SelectionSets("CurrentSelection").Delete
        Set UsersSelection = .SelectionSets.add("CurrentSelection")
        
        FilterType(0) = 0
        FilterData(0) = "Arc"
        
        UsersSelection.SelectOnScreen FilterType, FilterData
        
        
        count = getEntitySize(UsersSelection, "AcDbArc")
        
        For i = 0 To count
            Set arcObjs = UsersSelection.Item(i)
            Exit For
        Next i
        
        
    End With
    
    Set selectArcObj = arcObjs

End Function

 

Function selectPolyline()

    Dim newroad As AcadEntity
    Dim basePnt1 As Variant
        
    On Error GoTo start
    
start:
    ThisDrawing.Utility.getEntity newroad, basePnt1, "Get Object1: "
    
    
    Debug.Print ""
    
    

End Function


Function selectObjs() As AcadEntity()
    Dim UsersSelection As AcadSelectionSet
    Dim FilterType(0) As Integer
    Dim FilterData(0) As Variant
    Dim arcObjs() As AcadEntity
 
     With ThisDrawing
        On Error Resume Next
        
        .SelectionSets("CurrentSelection").Delete
        Set UsersSelection = .SelectionSets.add("CurrentSelection")
        
        UsersSelection.SelectOnScreen
        
        ReDim arcObjs(0 To UsersSelection.count - 1) As AcadEntity
        For i = 0 To UsersSelection.count
            Set arcObjs(i) = UsersSelection.Item(i)
        Next i
        
        
    End With
    
    selectObjs = arcObjs

End Function


Function selectEntity() As AcadEntity
    Dim UsersSelection As AcadSelectionSet
    Dim FilterType(0) As Integer
    Dim FilterData(0) As Variant
    Dim arcObjs() As AcadEntity
    Dim returnObj1 As AcadObject
    Dim basePnt1 As Variant
 
    ThisDrawing.Utility.getEntity returnObj1, basePnt1, "Get Object: "
    
    Set selectEntity = returnObj1

End Function


Function selectSubEntity() As AcadEntity
    Dim UsersSelection As AcadSelectionSet
    Dim FilterType(0) As Integer
    Dim FilterData(0) As Variant
    Dim arcObjs() As AcadEntity
    Dim returnObj1 As AcadObject
    Dim basePnt1 As Variant
 
    ThisDrawing.Utility.GetSubEntity
    
    selectObj = returnObj1

End Function


Function selectlineObs() As AcadEntity()
    Dim UsersSelection As AcadSelectionSet
    Dim FilterType(0) As Integer
    Dim FilterData(0) As Variant
    Dim arcObjs() As AcadEntity
 
     With ThisDrawing
        On Error Resume Next
        
        .SelectionSets("CurrentSelection").Delete
        Set UsersSelection = .SelectionSets.add("CurrentSelection")
        
        FilterType(0) = 0
        FilterData(0) = "Line"
        
        UsersSelection.SelectOnScreen FilterType, FilterData
        
        
        count = getEntitySize(UsersSelection, "AcDbLine")
        
        ReDim arcObjs(0 To count - 1) As AcadEntity
        
        For i = 0 To count
            Set arcObjs(i) = UsersSelection.Item(i)
        Next i
        
        
    End With
    
    selectlineObs = arcObjs

End Function



Function selectPolylineObs() As AcadEntity()
    Dim UsersSelection As AcadSelectionSet
    Dim FilterType(0) As Integer
    Dim FilterData(0) As Variant
    Dim arcObjs() As AcadEntity
    Dim retObjs() As AcadEntity
    Dim ent As AcadEntity
    Dim retCnt As Integer
    retCnt = 0
 
     With ThisDrawing
        On Error Resume Next
        
        .SelectionSets("CurrentSelection").Delete
        Set UsersSelection = .SelectionSets.add("CurrentSelection")
        
        FilterType(0) = 0
        FilterData(0) = "LWPolyline"
        
        UsersSelection.SelectOnScreen FilterType, FilterData
        
        
        count = getEntitySize(UsersSelection, "AcDbPolyline")
        
        ReDim arcObjs(0 To count - 1) As AcadEntity
        
        For i = 0 To count - 1
            Set ent = UsersSelection.Item(i)
            If ent.Closed = True Then
                retCnt = retCnt + 1
            End If
        Next i
        
        ReDim retObjs(0 To retCnt - 1) As AcadEntity
        
        retCnt = 0
        
        For i = 0 To count - 1
            Set ent = UsersSelection.Item(i)
            If ent.Closed = True Then
                Set retObjs(retCnt) = ent
                retCnt = retCnt + 1
            End If
        Next i
        
        
    End With
    
    selectPolylineObs = retObjs

End Function



Function selectPLObjs() As AcadEntity()
    Dim UsersSelection As AcadSelectionSet
    Dim FilterType(0) As Integer
    Dim FilterData(0) As Variant
    Dim arcObjs() As AcadEntity
 
 
     With ThisDrawing
        On Error Resume Next
        
        .SelectionSets("CurrentSelection").Delete
        Set UsersSelection = .SelectionSets.add("CurrentSelection")
        
        FilterType(0) = 0
        FilterData(0) = "LWPolyline"
        
        UsersSelection.SelectOnScreen FilterType, FilterData
        
        
        count = getEntitySize(UsersSelection, "AcDbPolyline")
        
        ReDim arcObjs(0 To count - 1) As AcadEntity
        
        For i = 0 To count
            Set arcObjs(i) = UsersSelection.Item(i)
        Next i
        
        
    End With
    
    selectPLObjs = arcObjs

End Function


Function selectPLObj() As AcadEntity
    Dim UsersSelection As AcadSelectionSet
    Dim FilterType(0) As Integer
    Dim FilterData(0) As Variant
    Dim retobj As AcadEntity
 
     With ThisDrawing
        On Error Resume Next
        
        .SelectionSets("CurrentSelection").Delete
        Set UsersSelection = .SelectionSets.add("CurrentSelection")
        
        FilterType(0) = 0
        FilterData(0) = "LWPolyline"
        
        UsersSelection.SelectOnScreen FilterType, FilterData
        
        
        count = getEntitySize(UsersSelection, "AcDbPolyline")
        
        If count > 0 Then
            Set retobj = UsersSelection.Item(0)
        End If
        
        
    End With
    
    Set selectPLObj = retobj


End Function

Attribute VB_Name = "showdebug"



Function addDonutCheck(ByVal x1 As Double, ByVal y1 As Double)

    Dim circleobj As AcadCircle
    Dim centerPoint(0 To 2) As Double
    
     
     centerPoint(0) = x1
    centerPoint(1) = y1
    
    Set circleobj = ThisDrawing.ModelSpace.AddCircle(centerPoint, 5)
    circleobj.color = acMagenta
    circleobj.Update
  
    

End Function


Function addDonut(ByVal x1 As Double, ByVal y1 As Double)

    
    Dim circleobj As AcadCircle
    Dim centerPoint(0 To 2) As Double
     
    If SHOW_CIRCLE = True Then
        centerPoint(0) = x1
        centerPoint(1) = y1
        
        Set circleobj = ThisDrawing.ModelSpace.AddCircle(centerPoint, 1)
        circleobj.Update
    End If

End Function

Function addDonut_2(ByVal x1 As Double, ByVal y1 As Double)

    Dim circleobj As AcadCircle
    Dim centerPoint(0 To 2) As Double
    
 
    If SHOW_CIRCLE = True Then
        centerPoint(0) = x1
        centerPoint(1) = y1
        
        Set circleobj = ThisDrawing.ModelSpace.AddCircle(centerPoint, 0.5)
        circleobj.Update
    End If
    

End Function

Function addDonut3(ByVal x1 As Double, ByVal y1 As Double)

    Dim circleobj As AcadCircle
    Dim centerPoint(0 To 2) As Double
    
    
    If SHOW_CIRCLE = True Then
        centerPoint(0) = x1
        centerPoint(1) = y1
        
        Set circleobj = ThisDrawing.ModelSpace.AddCircle(centerPoint, 0.5)
        circleobj.Update
    End If
    

End Function

Function addDonut5(ByVal x1 As Double, ByVal y1 As Double) As AcadCircle

    Dim circleobj As AcadCircle
    Dim centerPoint(0 To 2) As Double
    
 
    'If SHOW_CIRCLE = True Then
        centerPoint(0) = x1
        centerPoint(1) = y1
        
        Set circleobj = ThisDrawing.ModelSpace.AddCircle(centerPoint, 0.5)
        circleobj.Update
    'End If
    
    Set addDonut5 = circleobj

End Function

Function addDonut9(ByVal x1 As Double, ByVal y1 As Double)

    Dim circleobj As AcadCircle
    Dim centerPoint(0 To 2) As Double
    
 
    'If SHOW_CIRCLE = True Then
        centerPoint(0) = x1
        centerPoint(1) = y1
        
        Set circleobj = ThisDrawing.ModelSpace.AddCircle(centerPoint, 0.3)
        circleobj.Update
    'End If
    

End Function


Function addDonutR(ByVal x1 As Double, ByVal y1 As Double)

    Dim circleobj As AcadCircle
    Dim centerPoint(0 To 2) As Double
    
 
    If SHOW_CIRCLE = True Then
        centerPoint(0) = x1
        centerPoint(1) = y1
        
        Set circleobj = ThisDrawing.ModelSpace.AddCircle(centerPoint, 0.8)
        circleobj.color = acRed
        circleobj.Update
    End If
    

End Function


Function addDonutY(ByVal x1 As Double, ByVal y1 As Double)

    Dim circleobj As AcadCircle
    Dim centerPoint(0 To 2) As Double
    
    
 
    If SHOW_CIRCLE = True Then
         centerPoint(0) = x1
        centerPoint(1) = y1
        
        Set circleobj = ThisDrawing.ModelSpace.AddCircle(centerPoint, 0.7)
        circleobj.color = acYellow
        circleobj.Update
    End If
    

End Function


Function addDonutA(ByVal x1 As Double, ByVal y1 As Double)

    Dim circleobj As AcadCircle
    Dim centerPoint(0 To 2) As Double
    
    
 
         centerPoint(0) = x1
        centerPoint(1) = y1
        
        Set circleobj = ThisDrawing.ModelSpace.AddCircle(centerPoint, 0.7)
        circleobj.color = acMagenta
        circleobj.Update
    

End Function



Function addDonutB(ByVal x1 As Double, ByVal y1 As Double)

    Dim circleobj As AcadCircle
    Dim centerPoint(0 To 2) As Double
    
 
    If SHOW_CIRCLE = True Then
        centerPoint(0) = x1
        centerPoint(1) = y1
        
        Set circleobj = ThisDrawing.ModelSpace.AddCircle(centerPoint, 0.6)
        circleobj.color = acBlue
        circleobj.Update
    End If
    

End Function



Function addDonutG(ByVal x1 As Double, ByVal y1 As Double)

    Dim circleobj As AcadCircle
    Dim centerPoint(0 To 2) As Double
    
 
    If SHOW_CIRCLE = True Then
        centerPoint(0) = x1
        centerPoint(1) = y1
        
        Set circleobj = ThisDrawing.ModelSpace.AddCircle(centerPoint, 1)
        circleobj.color = acGreen
        circleobj.Update
    End If
    

End Function


Function addLine(pts() As Double) As AcadEntity

    Dim ent As AcadEntity
    

    Set ent = ThisDrawing.ModelSpace.AddLightWeightPolyline(pts)

    Set addLine = ent

End Function

Attribute VB_Name = "topology"

Function getFarPoint1(list() As clsPoint, pt As clsPoint) As clsPoint

    Dim p As clsPoint
    Dim dd As Double
    Dim max As Double
    Dim idx As Integer
    
    max = 0
    
    For i = 0 To UBound(list)
    
        p = list(0)
        dd = pt.distance(p)
        
        If dd > max Then
            max = dd
            idx = i
            
        End If
        
    Next


    getFarPoint1 = list(idx)


End Function

Function getFarPoint2(list As Variant, pt As clsPoint) As clsPoint

    Dim p As New clsPoint
    Dim dd As Double
    Dim idx As Integer
    Dim x As Double
    Dim y As Double
    
    max = 0
    
     
    
    For i = 0 To UBound(list) Step 3
    
        x = list(i)
        y = list(i + 1)
    
        p.initXy x, y 'x, y
        
        
        dd = pt.distance(p)
        
        If dd > max And dd < FAR_OVER Then
            max = dd
            idx = i
            
        End If
        
    Next

    p.initXy list(idx), list(idx + 1)


    Set getFarPoint2 = p


End Function





'intersectwith에서 잘못된점이 있기때문에 생성
Function getFarPoint2Ex(ent As AcadEntity, list As Variant, pt As clsPoint) As clsPoint

    Dim p As New clsPoint
    Dim dd As Double
    Dim idx As Integer
    Dim x As Double
    Dim y As Double
    Dim exists As Boolean
    
    Dim cpt As New clsPoint
    Dim newpr As New clsPolygonReader
    
    Dim ddd() As Double
    Dim d1 As Double
    Dim d2 As Double
    
    Dim tmp As AcadLWPolyline
    
    max = 0
    
     
    newpr.init ent
    newpr.setIndexByPoint pt
    
    'addDonut5 pt.x, pt.y
    
    For i = 0 To UBound(list) Step 3
    
        x = list(i)
        y = list(i + 1)
    
        
    
        exists = isContains(ent, x, y)
    
        If exists = True Then
            
            p.initXy x, y 'x, y
            'addDonutA x, y
            
            newpr.setEIndexByPoint p
            
            ddd = newpr.getLongLine2
            'Set tmp = ThisDrawing.ModelSpace.AddLightWeightPolyline(ddd)
            d1 = getArrayDistance(ddd)
            
            ddd = newpr.getShortLine2
            'Set tmp = ThisDrawing.ModelSpace.AddLightWeightPolyline(ddd)
            d2 = getArrayDistance(ddd)
            
            
            If d1 > d2 Then
                dd = d2
            Else
                dd = d1
            End If
            
            'Debug.Print ">>>>>> " & d1 & ", " & d2 & ">>>>> " & dd
            
            'dd = pt.distance(p)
            
            If dd > max And dd < FAR_OVER Then
                max = dd
                idx = i
                
            End If
        End If
        
    Next

    p.initXy list(idx), list(idx + 1)


    Set getFarPoint2Ex = p


End Function



Function getNearPoint2(list As Variant, pt As clsPoint) As clsPoint

    Dim p As New clsPoint
    Dim dd As Double
    Dim idx As Integer
    Dim x As Double
    Dim y As Double
    
    min = 99999999
    
    For i = 0 To UBound(list) Step 3
    
        x = list(0)
        y = list(1)
    
        p.initXy list(i), list(i + 1) 'x, y
        
        dd = pt.distance(p)
        
        If dd < min Then
            min = dd
            idx = i
            
        End If
        
    Next

    p.initXy list(idx), list(idx + 1)


    Set getNearPoint2 = p


End Function


Function getLineByEntity(ent As AcadEntity, ByVal vx As Double, ByVal vy As Double) As AcadLine

    Dim newv(0 To 1) As Double
    Dim ddd() As Double
    Dim count As Integer
    Dim distance As Double

    Dim ret As Boolean
    Dim newp() As Double
    Dim line As AcadLine
    
    newv(0) = vx: newv(1) = vy
    ret = False
    
    addDonutR vx, vy
    ddd = ent.Coordinates
    count = UBound(ddd)
    
    x1 = ddd(count - 1)
    y1 = ddd(count)
    
    For ii = 0 To count Step 2
    
        x2 = ddd(ii)
        y2 = ddd(ii + 1)
        
        f = getTan(x1, x2, y1, y2)
        f1 = getTan(x1, vx, y1, vy)
        f2 = getTan(vx, x2, vy, y2)
         
        fd = XYDistance(x1, y1, x2, y2)
        fd1 = XYDistance(x1, y1, vx, vy) + XYDistance(x2, y2, vx, vy)
        
        If Abs(fd - fd1) < PD_TOL Then
            
            newp = crossXY(vx, vy, x1, y1, x2, y2)
            
            
            Dim sp(0 To 2) As Double
            Dim ep(0 To 2) As Double
            
            
            sp(0) = x1
            sp(1) = y1
            ep(0) = x2
            ep(1) = y2
            
            Set line = ThisDrawing.ModelSpace.addLine(sp, ep)
      
            
            addDonutY vx, vy
            
            Exit For
        
        End If
        
        x1 = x2
        y1 = y2
        
    Next ii
    
    If ret = False Then
        newv(0) = 0
        newv(1) = 0
    
    End If
        
   
    
    
    Set getLineByEntity = line
        
        
    
End Function


Function searchCrossVertext(src As AcadEntity, dst As AcadEntity) As Double()

    
    searchCrossVertext = src.IntersectWith(dst, acExtendNone)   'find vertex
     
    
End Function

Function searchCrossVertextEx(src As AcadEntity, dst As AcadEntity) As Double()

    Dim size As Integer
    Dim d3 As Variant
    Dim ret() As Double
    Dim ret2() As Double
    Dim vx, vy As Variant
    Dim b1, b2 As Boolean
    Dim idx As Integer
    Dim cnt As Integer
    
    idx = 0
    
    d3 = src.IntersectWith(dst, acExtendNone)   'find vertex
    
    size = UBound(d3)
    ReDim ret(size) As Double
    
    For i = 0 To size Step 3
    
        vx = d3(i)
        vy = d3(i + 1)
        
        b1 = isContains(src, CDbl(vx), CDbl(vy))
        b2 = isContains(dst, CDbl(vx), CDbl(vy))
        
        If b1 = True And b2 = True Then
        
            ret(idx) = vx
            ret(idx + 1) = vy
            ret(idx + 2) = 0
            
            idx = idx + 3
            cnt = cnt + 1
        
        End If
    
    Next
    
    ReDim ret2(0 To cnt * 3 - 1) As Double
    
    For i = 0 To cnt * 3 - 1 Step 3
    
        ret2(i) = ret(i)
        ret2(i + 1) = ret(i + 1)
        ret2(i + 2) = ret(i + 2)
    
    Next
    
    
    
    searchCrossVertextEx = ret2
    
End Function



Function isContains(src As AcadEntity, vx As Double, vy As Double) As Boolean

    Dim ddd() As Double
    Dim x, y As Double
    Dim ret As Boolean
    Dim b As Boolean
    
    ret = False
    ddd = src.Coordinates
   
    
    For i = 0 To UBound(ddd) - 1 Step 2
    
        x = ddd(i)
        y = ddd(i + 1)
        
        
        'addDonut5 x, y
        
        b = isEqualsDouble(CDbl(x), y, vx, vy)
        
        'If x = vx And y = vy Then
        If b = True Then
            ret = True
            Exit For
        End If
    
    
    Next
    
    isContains = ret


End Function


Function getArrayDistance(d() As Double) As Double

    Dim ret As Double
    Dim size As Integer
    Dim x1, y1, x2, y2 As Double
        
    ret = 0
    size = UBound(d)
    
    If size = 0 Then
        Return
    End If

    x1 = d(0)
    y1 = d(1)
    
    For i = 2 To size Step 2
    
        x2 = d(i)
        y2 = d(i + 1)
        
        ret = ret + getDistance(x1, y1, x2, y2)
        
        x1 = x2
        y1 = y2
       
    Next
    
    getArrayDistance = ret

End Function

Function trimArrayDouble(ddd() As Double) As Double()

    Dim size As Integer
    Dim idx As Integer
    Dim ret() As Double
    
    idx = -1
    size = UBound(ddd)
    
    
    For i = 0 To size - 1
    
        If ddd(i) = 0 And ddd(i + 1) = 0 Then
            idx = i
            Exit For
        End If
        
    Next
    

    
    If idx = -1 Then
    
        trimArrayDouble = ddd
    Else
    
    
        ReDim ret(idx - 1) As Double
        
        For i = 0 To idx - 1
        
            ret(i) = ddd(i)
        
        Next
    
        trimArrayDouble = ret
    End If
    


End Function


Function trimPolyline(ent As AcadLWPolyline) As AcadLWPolyline

    Dim retent As AcadLWPolyline

    Dim ddd() As Double
    Dim ddd2() As Double
    Dim ddd3() As Double
    
    Dim x1, y1, x2, y2 As Double
    Dim size As Integer
    Dim idx As Integer
    
    idx = 0
    ddd = ent.Coordinates
    size = UBound(ddd)
    
    ReDim ddd2(size) As Double
    
    x1 = ddd(0)
    y1 = ddd(1)
    
    ddd2(0) = x1
    ddd2(1) = y1
    
    idx = idx + 2
    
    For i = 2 To UBound(ddd) Step 2
    
        x2 = ddd(i)
        y2 = ddd(i + 1)
    
        If x1 = x2 And y1 = y2 Then
            Debug.Print ""
            
        Else
            ddd2(idx) = x2
            ddd2(idx + 1) = y2
        
            idx = idx + 2
        End If
        
        x1 = x2
        y1 = y2
    
    
    Next
    
    
    ddd3 = trimArrayDouble(ddd2)
    
    Debug.Print ""
    
    Set retent = ThisDrawing.ModelSpace.AddLightWeightPolyline(ddd3)
    retent.Closed = True
    
    Set trimPolyline = retent

End Function


Function polyline2lwpolyline(src As AcadEntity) As AcadLWPolyline


    Dim size As Integer
    Dim ret As AcadLWPolyline
    Dim ddd() As Double
    Dim ddd2() As Double
    Dim idx As Integer
    
    ddd = src.Coordinates
    size = UBound(ddd)
    
    
    ReDim ddd2(size * 2 / 3) As Double
    
    For i = 0 To size Step 3
    
        ddd2(idx) = ddd(i)
        ddd2(idx + 1) = ddd(i + 1)
        
        idx = idx + 2
    
    Next i
    
    Set ret = ThisDrawing.ModelSpace.AddLightWeightPolyline(ddd2)
    If ret.Closed = False Then
        ret.Closed = True
    End If
    
    

End Function


Function d3ToPolyline(ddd As Variant) As AcadLWPolyline


    Dim size As Integer
    Dim ret As AcadLWPolyline
    Dim ddd2() As Double
    Dim idx As Integer
    
     
    size = UBound(ddd)
    
    
    ReDim ddd2(size * 2 / 3) As Double
    
    For i = 0 To size Step 3
    
        ddd2(idx) = ddd(i)
        ddd2(idx + 1) = ddd(i + 1)
        
        idx = idx + 2
    
    Next i

    Set ret = ThisDrawing.ModelSpace.AddLightWeightPolyline(ddd2)
    If ret.Closed = False Then
        ret.Closed = True
    End If
    
    Set d3ToPolyline = ret
    

End Function



Function toEntityArray(col As Collection) As AcadEntity()
  Dim arr() As AcadEntity
  ReDim arr(0 To col.count - 1) As AcadEntity
  For i = 1 To col.count
      Set arr(i - 1) = col(i)
  Next
  toEntityArray = arr
End Function


Function expoldeRegion(reg As Variant) As AcadEntity()

    Dim has As Boolean
    Dim conv As New ClsConverter
    Dim pl As AcadLWPolyline
    Dim Punto As Variant
    Dim retents() As AcadEntity
    Dim col As New Collection

    has = hasSubRegion(reg)
    
    If has = True Then
    
        Punto = reg.Explode
        reg.Delete
        
        For i = 0 To UBound(Punto)
            Set pl = conv.reg2polyline(Punto(i))
            col.add pl
        Next i
        
        For i = 0 To UBound(Punto)
            Punto(i).Delete
        Next i
        
        
        retents = toEntityArray(col)
    
    Else
    
        ReDim retents(0) As AcadEntity
        Set retents(0) = conv.reg2polyline(reg)
        reg.Delete
    
    End If
    
    
    expoldeRegion = retents

End Function

Function expoldeRegionEx(reg As Variant, color As Variant)

    Dim has As Boolean
    Dim conv As New ClsConverter
    Dim pl As AcadLWPolyline
    Dim Punto As Variant

    has = hasSubRegion(reg)
    
    If has = True Then
    
        Punto = reg.Explode
        reg.Delete
        
        For i = 0 To UBound(Punto)
            Set pl = conv.reg2polyline(Punto(i))
            pl.color = color
        Next i
        
        For i = 0 To UBound(Punto)
            Punto(i).Delete
        Next i
    
    Else
    
        Set pl = conv.reg2polyline(reg)
        pl.color = color
        
        reg.Delete
    
    End If
    


End Function


Function hasSubRegion(reg As Variant) As Boolean

    Dim arr As Variant
    Dim size As Integer
    Dim ret As Boolean

    ret = True

    arr = reg.Explode
    size = UBound(arr)
    
    If size > 0 Then
        If TypeOf arr(0) Is AcadLine Then
            ret = False
        
        End If
    End If
    
    
    For i = 0 To size
        arr(i).Delete
    
    Next
    
    hasSubRegion = ret

End Function


Function sublwpolyline(sx As Double, sy As Double, ent As AcadLWPolyline) As AcadLWPolyline


    Dim ddd() As Double
    Dim size As Integer
    Dim sidx As Integer
    Dim x, y As Double
    
    Dim ddd2() As Double
    
    Dim retent As AcadLWPolyline
    
    ddd = ent.Coordinates
    size = UBound(ddd)
    
    sidx = 0
    
    For i = 0 To size Step 2
        x = ddd(i)
        y = ddd(i + 1)
        
        If sx = x And sy = y Then
            Exit For
        End If
    
        sidx = sidx + 2
    Next i
    
    
    ReDim ddd2(size - sidx) As Double
    
    For i = sidx To size Step 2
        ddd2(i - sidx) = ddd(i)
        ddd2(i - sidx + 1) = ddd(i + 1)
        
    Next i
    
    Set retent = ThisDrawing.ModelSpace.AddLightWeightPolyline(ddd2)
    
    
    Set sublwpolyline = retent


End Function


Function extendLine(x1 As Double, y1 As Double, x2 As Double, y2 As Double, delta As Double) As AcadEntity

    Dim dx As Double
    Dim dy As Double
    Dim retd(2) As Double
    Dim ret As AcadEntity
    Dim sp(2) As Double
    
    sp(0) = x1
    sp(1) = y1
    
    dx = x2 - x1
    dy = y2 - y1
    
    retd(0) = x1 + dx * delta
    retd(1) = y1 + dy * delta
    
    Set ret = ThisDrawing.ModelSpace.addLine(sp, retd)
    ret.color = acRed
    
    Set extendLine = ret

End Function

Function extendLineBoth(x1 As Double, y1 As Double, x2 As Double, y2 As Double, cx As Double, cy As Double, delta As Double) As AcadEntity

    Dim dx As Double
    Dim dy As Double
    Dim retd(2) As Double
    Dim ret As AcadEntity
    Dim sp(2) As Double
    Dim dist As Double
    
    dx = x2 - x1
    dy = y2 - y1
    
    
    dist = getDistance(x1, y1, x2, y2)
    
    delta = delta / dist
    
    retd(0) = cx + dx * delta
    retd(1) = cy + dy * delta
    
    sp(0) = cx - dx * delta
    sp(1) = cy - dy * delta
    
    Set ret = ThisDrawing.ModelSpace.addLine(sp, retd)
    ret.color = acRed
    
    Set extendLineBoth = ret

End Function

Function getNearestTwo(ddd3() As Double, x As Double, y As Double) As Double()


    Dim ret(3) As Double
    Dim dist1 As Double
    Dim dist2 As Double
    Dim idx1 As Integer
    Dim idx2 As Integer
    Dim dist As Double
    Dim vx As Double
    Dim vy As Double
    
    dist1 = 99999
    dist2 = 99999
    
    For i = 0 To UBound(ddd3) Step 3
        vx = ddd3(i)
        vy = ddd3(i + 1)
    
        dist = getDistance(vx, vy, x, y)
    
        If dist < dist1 Then
            idx2 = idx1
            dist2 = dist1
            
            idx1 = i
            dist1 = dist
            
        ElseIf dist < dist2 Then
            idx2 = i
            dist2 = dist
        End If
        
    
    Next


    ret(0) = ddd3(idx1)
    ret(1) = ddd3(idx1 + 1)
    ret(2) = ddd3(idx2)
    ret(3) = ddd3(idx2 + 1)

    getNearestTwo = ret

End Function


Function reversePoint2d(ddd() As Double) As Double()

    
    
    Dim ret() As Double
    Dim size As Integer
    
    
    size = UBound(ddd)
    ReDim ret(size) As Double
    
    For i = 0 To size Step 2
    
        ret(i) = ddd(size - i - 1)
        ret(i + 1) = ddd(size - i)
    
    
    
    Next
    
    
    reversePoint2d = ret
    


End Function

'직교 확인
Function isOrthogonalRadian(rad As Double) As Boolean

    Dim absrad As Double
    Dim retb As Boolean
    
    
    retb = False
    
    absrad = Abs(Abs(rad) - PI)
    
    
    If Abs(PI_2 - absrad) < 0.0000001 Then
        retb = True
    End If
    
    isOrthogonalRadian = retb
    
End Function


'느슨한 직교 확인
Function isLooseOrthogonalRadian(rad As Double) As Boolean

    Dim absrad As Double
    Dim retb As Boolean
    
    
    retb = False
    
    absrad = Abs(Abs(rad) - PI)
    
    
    If Abs(PI_2 - absrad) < 0.5 Then
        retb = True
    End If
    
    isLooseOrthogonalRadian = retb
    
End Function



Sub topologyTest()

    Dim p1 As New clsPoint
    Dim p2 As New clsPoint
    Dim distance As Double
    
    p1.initXy 0, 0
    p2.initXy 1, 1
    
    
    distance = p1.distance(p2)
    
    

End Sub




Function findLineAtPoint(ent As AcadEntity, ByVal vx As Double, ByVal vy As Double) As Double()

    Dim newv(0 To 3) As Double
    Dim ddd() As Double
    Dim count As Integer
    Dim distance As Double

    Dim ret As Boolean
    Dim newp() As Double
    
    Dim selidx As Integer
    Dim mindist As Double
    Dim exists As Boolean
    
    newv(0) = 0: newv(1) = 0
    ret = False
    
    
    exists = isContains(ent, vx, vy)
    
    If exists = False Then
        
        mindist = 999999
        
        'addDonutA vx, vy
        ddd = ent.Coordinates
        count = UBound(ddd)
        
        x1 = ddd(count - 1)
        y1 = ddd(count)
        
        For ii = 0 To count Step 2
        
            x2 = ddd(ii)
            y2 = ddd(ii + 1)
            
            f = getTan(x1, x2, y1, y2)
            f1 = getTan(x1, vx, y1, vy)
            f2 = getTan(vx, x2, vy, y2)
             
            fd = XYDistance(x1, y1, x2, y2)
            fd1 = XYDistance(x1, y1, vx, vy) + XYDistance(x2, y2, vx, vy)
 
            
            If Abs(fd - fd1) < mindist Then
                mindist = Abs(fd - fd1)
                newv(0) = x1
                newv(1) = y1
                newv(2) = x2
                newv(3) = y2
                selidx = ii
            
            End If
           
            x1 = x2
            y1 = y2
            
        Next ii
        
        If mindist < PD_TOL Then
            ret = True
        End If
        
        If ret = False Then
            newv(0) = 0
            newv(1) = 0
            newv(2) = 0
            newv(3) = 0
            Debug.Print "================NOT FOUND================"
        End If
    End If
    
    findLineAtPoint = newv
        
End Function
