Attribute VB_Name = "ClsChamfer"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private oldroad As AcadEntity
Private newroad As AcadEntity
Private fillet As AcadEntity

Private ptIntersection As Variant


Public Function load()

    Dim p1 As New clsPoint
    Dim p2() As Double
    Dim p3 As New clsPoint
    Dim retArc As AcadEntity
    Dim tmp As Variant
    
    
    Dim np1 As New clsPoint
    Dim np2 As New clsPoint
    Dim np3 As New clsPoint
    
    Dim splitter As New clsSplitter
    Dim pr As New clsPolygonReader
    
    Dim newroadsplit() As Double
    Dim oldroadsplit() As Double
    Dim filletsplit() As Double
    
    Dim merge As New ClsMerger
    Dim resultd() As Double
    Dim result As AcadEntity
    Dim test As Boolean
    
    
    ThisDrawing.SetVariable "osmode", 512
    ThisDrawing.Utility.getEntity newroad, tmp, "Enter a point 1: "
        
    p1.initPt tmp
     
    ThisDrawing.SetVariable "osmode", 512
    ThisDrawing.Utility.getEntity oldroad, tmp, "Enter a point 3: "
    
    p3.initPt tmp
    
    
    Debug.Print "p1: " & p1.x & ", " & p1.y
    Debug.Print "p3: " & p3.x & ", " & p3.y
    
    
    addDonut5 p1.x, p1.y
    addDonut5 p3.x, p3.y
    
    Dim vlist(0 To 3) As Double
    
    vlist(0) = p1.x
    vlist(1) = p1.y
    vlist(2) = p3.x
    vlist(3) = p3.y
    
    
    
    Set retArc = ThisDrawing.ModelSpace.AddLightWeightPolyline(vlist)
    
    'retArc.Delete
    
    
    Debug.Print "fillet created"
    
    
    ptIntersection = searchCrossVertext(newroad, oldroad)
    
    newp1 = findVertex(newroad, retArc)   '아크와 도로(새도로)의 접점 추가
    newp2 = findVertex(oldroad, retArc)   '아크와 도로(구도로)의 접점 추가
   
   
    np1.initXy newp1(0), newp1(1)
    np2.initXy newp2(0), newp2(1)
    
    
    Debug.Print "np1: " & np1.x & ", " & np1.y
    Debug.Print "np2: " & np2.x & ", " & np2.y
    
   
    Set np3 = getFarPoint2(ptIntersection, np2)     '기존도로 아크 접점에서 먼 지점을 찾는다
    
    
    addVertex oldroad, np3.x, np3.y     '기존도로에 접점추가
    

   
    Debug.Print "cross point created"
    
    pr.init newroad
    pr.setIndexByPoint np1
    pr.checkDirection p3
    
    'addDonut5 np3.x, np3.y
    'addDonut5 np1.x, np1.y
    Debug.Print "newroad direction processed"
    
    newroadsplit = pr.splitInnerLine(np3, np1)
    'addLine newroadsplit
    
    Debug.Print "newroad split created"
   
    pr.init oldroad
    pr.setIndexByPoint np2
    pr.checkDirection p1
    
    Debug.Print "oldroad direction processed"
    
    oldroadsplit = pr.splitInnerLine(np2, np3)
    'addLine oldroadsplit
    
    
    
    Debug.Print "oldroad split created"
        
     size1 = UBound(newroadsplit)
    size2 = UBound(vlist)
    size3 = UBound(oldroadsplit)
    
    merge.setSize size1 + size2 + size3 + 2
    
    
    merge.add newroadsplit
    merge.add vlist
    merge.add oldroadsplit
    
    
    addLine merge.getMerged
    newroad.Delete
    retArc.Delete
    
    
    
    'ThisDrawing.SendCommand "sob" & vbCr
    
End Function

Attribute VB_Name = "ClsFillet2"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private oldroad As AcadEntity
Private newroad As AcadEntity
Private fillet As AcadEntity

Private ptIntersection As Variant


Public Function load()

    Dim retArc As AcadEntity
    Dim tmp As Variant
    
    
    Dim np1 As New clsPoint
    Dim np2 As New clsPoint
    Dim np3 As New clsPoint
    
    Dim splitter As New clsSplitter
    Dim pr As New clsPolygonReader
    
    Dim newroadsplit() As Double
    Dim oldroadsplit() As Double
    Dim filletsplit() As Double
    
    Dim merge As New ClsMerger
    Dim resultd() As Double
    Dim test As Boolean
    
    Dim pt1 As New clsPoint
    Dim pt3 As New clsPoint
    
    
    Dim pr1 As New clsPolygonReader
    Dim pr2 As New clsPolygonReader
    
    Dim line1 As AcadLine
    Dim line2 As AcadLine
    Dim resultpl As AcadLine
    Dim ssetObj As AcadSelectionSet
    Dim result As AcadEntity

  
    Dim selec1 As New ClsSelEntity
    Dim selec2 As New ClsSelEntity
    
    
    Dim seler As New ClsSelReal
    Dim frad As Double
    
    Dim selecs As New clsSelSets
    
    selec1.selectPolyline ("Get Polyline 1: ")
    Set newroad = selec1.getEntity
    Set pt1 = selec1.getPoint
    
    selec2.selectPolyline ("Get Polyline 2: ")
    Set oldroad = selec2.getEntity
    Set pt3 = selec2.getPoint
    
    
    ptIntersection = searchCrossVertext(newroad, oldroad)
    
    Set np3 = getNearPoint2(ptIntersection, pt3)
    
    'addDonut5 pt1.x, pt1.y
    'addDonut5 pt3.x, pt3.y
    'addDonut5 np3.x, np3.y
    
    
    pr1.init newroad
    Set line1 = pr1.getLine(pt1)
    
     
    pr2.init oldroad
    Set line2 = pr2.getLine(pt3)
    
     
    
    Set resultpl = getShortestLine(line2, pt3, np3)
    
    
    frad = seler.selectFilletRadius
    
    
    Application.ActiveDocument.SendCommand "_fillet" & vbCr & "T" & vbCr & "N" & vbCr & "r" & vbCr & frad & vbCr & "(HandEnt """ & line1.Handle & """)" & vbCr & "(HandEnt """ & resultpl.Handle & """)" & vbCr
    
    
    Set retArc = selecs.selectArc
    
    'Set retArc = selectArcObj
    
    'Set ssetObj = ThisDrawing.ActiveSelectionSet
    '
    'ssetObj.Select acSelectionSetLast
    '
    'For Each ent In ssetObj
    '   Set retArc = ent
    'Next
    
    If line2.Handle <> resultpl.Handle Then
        resultpl.Delete
    End If
    
    line1.Delete
    line2.Delete
    
    
    
    Set fillet = arc2line(retArc)  '아크를 라인으로 변경
    filletsplit = fillet.Coordinates
    
    retArc.Delete
    
    
    Debug.Print "fillet created"
    
    
    ptIntersection = searchCrossVertext(newroad, oldroad)
    
    
    For i = 0 To UBound(ptIntersection) Step 3
        addDonutY ptIntersection(i), ptIntersection(i + 1)
        
    Next i
    
    newp1 = findVertex(newroad, fillet)   '아크와 도로(새도로)의 접점 추가
    newp2 = findVertex(oldroad, fillet)   '아크와 도로(구도로)의 접점 추가
   
   
    np1.initXy newp1(0), newp1(1)
    np2.initXy newp2(0), newp2(1)
    
    
    Debug.Print "np1: " & np1.x & ", " & np1.y
    Debug.Print "np2: " & np2.x & ", " & np2.y
    
    addDonutB np1.x, np1.y
    addDonutB np2.x, np2.y
   
    Set np3 = getFarPoint2(ptIntersection, np2)     '기존도로 아크 접점에서 먼 지점을 찾는다
    
    
    addVertex oldroad, np3.x, np3.y     '기존도로에 접점추가
    
    addDonutG np3.x, np3.y
     
    
    Debug.Print "cross point created"
    
    pr.init newroad
    pr.setIndexByPoint np1
    pr.checkDirection pt3
    
    'addDonut5 np3.x, np3.y
    'addDonut5 np1.x, np1.y
    Debug.Print "newroad direction processed"
    
    newroadsplit = pr.splitInnerLine(np3, np1)
    'addLine newroadsplit
 
    Debug.Print "newroad split created"
   
    pr.init oldroad
    pr.setIndexByPoint np2
    pr.checkDirection pt1
    
    Debug.Print "oldroad direction processed"
    
    oldroadsplit = pr.splitInnerLine(np2, np3)
    'addLine oldroadsplit

    
    Debug.Print "oldroad split created"
        
    size1 = UBound(newroadsplit)
    size2 = UBound(filletsplit)
    size3 = UBound(oldroadsplit)
    
    merge.setSize size1 + size2 + size3 + 2
    
    
    merge.add newroadsplit
    merge.add filletsplit
    merge.add oldroadsplit
    
    
    Set result = addLine(merge.getMerged)
    newroad.Delete
    fillet.Delete
    
    
    
    ThisDrawing.SendCommand "sob" & vbCr
    
    Set temp = ThisDrawing.ActiveLayer
    result.Layer = ThisDrawing.ActiveLayer.Name
    
    
End Function


Private Function getArcBy3P(p1() As Double, p2() As Double, p3() As Double) As AcadArc
    Dim centerPoint(0 To 2) As Double
    Dim retOjb As AcadArc
    
    x1 = p1(0)
    y1 = p1(1)
    
    x2 = p2(0)
    y2 = p2(1)
     
    x3 = p3(0)
    y3 = p3(1)
    
    d1 = (x2 - x1) / (y2 - y1)
    d2 = (x3 - x2) / (y3 - y2)
    
    cx = ((y3 - y1) + (x2 + x3) * d2 - (x1 + x2) * d1) / (2 * (d2 - d1))
    cy = -d1 * (cx - (x1 + x2) / 2) + (y1 + y2) / 2
     
    r = VBA.Sqr((x1 - cx) ^ 2 + (y1 - cy) ^ 2)
    
    centerPoint(0) = cx
    centerPoint(1) = cy
    
    StartAngle = ArcTan2((x1 - cx), (y1 - cy))
    EndAngle = ArcTan2((x3 - cx), (y3 - cy))
    
    If StartAngle >= 0 And EndAngle >= 0 Then
        If StartAngle > EndAngle Then
            tmp = StartAngle
            StartAngle = EndAngle
            EndAngle = tmp
        End If
    ElseIf StartAngle < 0 And EndAngle < 0 Then
        If StartAngle > EndAngle Then
            tmp = StartAngle
            StartAngle = EndAngle
            EndAngle = tmp
        End If
    ElseIf StartAngle > 0 And EndAngle < 0 Then
        If (PI - StartAngle) + (PI + EndAngle) > PI Then
            tmp = StartAngle
            StartAngle = EndAngle
            EndAngle = tmp
        End If
    ElseIf StartAngle < 0 And EndAngle > 0 Then
        If Abs(StartAngle) + EndAngle > PI Then
            tmp = StartAngle
            StartAngle = EndAngle
            EndAngle = tmp
        End If
            
    End If
    
    
    Set retOjb = ThisDrawing.ModelSpace.AddArc(centerPoint, r, StartAngle, EndAngle)
     
    
    Set getArcBy3P = retOjb

End Function

Attribute VB_Name = "ClsFilletT"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private oldroad As AcadEntity
Private newroad As AcadEntity
Private fillet As AcadEntity

Private ptIntersection As Variant


Public Function load()

    Dim retArc As AcadEntity
    Dim tmp As Variant
    
    
    Dim np1 As New clsPoint
    Dim np2 As New clsPoint
    Dim np3 As New clsPoint
    
    Dim splitter As New clsSplitter
    Dim pr As New clsPolygonReader
    
    Dim newroadsplit() As Double
    Dim oldroadsplit() As Double
    Dim filletsplit() As Double
    
    Dim merge As New ClsMerger
    Dim resultd() As Double
    Dim test As Boolean
    
    Dim pt1 As New clsPoint
    Dim pt3 As New clsPoint
    
    
    Dim pr1 As New clsPolygonReader
    Dim pr2 As New clsPolygonReader
    
    Dim line1 As AcadLine
    Dim line2 As AcadLine
    Dim resultpl As AcadLine
    Dim ssetObj As AcadSelectionSet
    Dim result As AcadEntity

  
    Dim selec1 As New ClsSelEntity
    Dim selec2 As New ClsSelEntity
    
    
    Dim seler As New ClsSelReal
    Dim frad As Double
    
    Dim selecs As New clsSelSets
    
    selec1.selectPolyline ("Get Polyline 1: ")
    Set newroad = selec1.getEntity
    Set pt1 = selec1.getPoint
    
    selec2.selectPolyline ("Get Polyline 2: ")
    Set oldroad = selec2.getEntity
    Set pt3 = selec2.getPoint
    
    
    
    
    ptIntersection = searchCrossVertext(newroad, oldroad)
    
    Set np3 = getNearPoint2(ptIntersection, pt3)
    
    'addDonut5 pt1.x, pt1.y
    'addDonut5 pt3.x, pt3.y
    'addDonut5 np3.x, np3.y
    
    
    pr1.init newroad
    Set line1 = pr1.getLine(pt1)
    
     
    pr2.init oldroad
    Set line2 = pr2.getLine(pt3)
    
     
    
    Set resultpl = getShortestLine(line2, pt3, np3)
    
    
    frad = seler.selectChamferDistance
    
    'Application.ActiveDocument.SendCommand "_chamfer" & vbCr & "D" & vbCr & "1" & vbCr & "1" & vbCr & "(HandEnt """ & line1.Handle & """)" & vbCr & "(HandEnt """ & line2.Handle & """)" & vbCr
    Application.ActiveDocument.SendCommand "_fillet" & vbCr & "T" & vbCr & "N" & vbCr & "r" & vbCr & frad & vbCr & "(HandEnt """ & line1.Handle & """)" & vbCr & "(HandEnt """ & resultpl.Handle & """)" & vbCr
    
    
    Set retArc = selecs.selectArc
    
    'Set retArc = selectArcObj
    
    'Set ssetObj = ThisDrawing.ActiveSelectionSet
    '
    'ssetObj.Select acSelectionSetLast
    '
    'For Each ent In ssetObj
    '   Set retArc = ent
    'Next
    
    If line2.Handle <> resultpl.Handle Then
        resultpl.Delete
    End If
    
    line1.Delete
    line2.Delete
    
    
    
    Set fillet = arc2line(retArc)  '아크를 라인으로 변경
    filletsplit = fillet.Coordinates
    
    retArc.Delete
    
    
    Debug.Print "fillet created"
    
    
    ptIntersection = searchCrossVertext(newroad, oldroad)
    
    
    For i = 0 To UBound(ptIntersection) Step 3
        addDonutY ptIntersection(i), ptIntersection(i + 1)
        
    Next i
    
    newp1 = findVertex(newroad, fillet)   '아크와 도로(새도로)의 접점 추가
    newp2 = findVertex(oldroad, fillet)   '아크와 도로(구도로)의 접점 추가
   
   
    np1.initXy newp1(0), newp1(1)
    np2.initXy newp2(0), newp2(1)
    
    
    Debug.Print "np1: " & np1.x & ", " & np1.y
    Debug.Print "np2: " & np2.x & ", " & np2.y
    
    addDonutB np1.x, np1.y
    addDonutB np2.x, np2.y
   
    Set np3 = getFarPoint2(ptIntersection, np2)     '기존도로 아크 접점에서 먼 지점을 찾는다
    
    
    addVertex oldroad, np3.x, np3.y     '기존도로에 접점추가
    
    addDonutG np3.x, np3.y
     
    
    Debug.Print "cross point created"
    
    pr.init newroad
    pr.setIndexByPoint np1
    pr.checkDirection pt3
    
    'addDonut5 np3.x, np3.y
    'addDonut5 np1.x, np1.y
    Debug.Print "newroad direction processed"
    
    newroadsplit = pr.splitInnerLine(np3, np1)
    addLine newroadsplit
 
    Debug.Print "newroad split created"
   
    pr.init oldroad
    pr.setIndexByPoint np2
    pr.checkDirection pt1
    
    Debug.Print "oldroad direction processed"
    
    oldroadsplit = pr.splitInnerLine(np2, np3)
    addLine oldroadsplit

    
    Debug.Print "oldroad split created"
        
     
    
End Function

Attribute VB_Name = "ClsMerger"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private ret() As Double
Private index As Integer



Public Function setSize(size As Integer)

    ReDim ret(0 To size) As Double
    index = 0

End Function


Public Function add(d() As Double)

    Dim reverse As Boolean
    Dim size As Integer
    
    reverse = False
    size = UBound(d)
    
    If index > 1 Then
    
        x = ret(index - 2)
        y = ret(index - 1)
        
        d1 = getDistance(x, y, d(0), d(1))
        d2 = getDistance(x, y, d(size - 1), d(size))
        
        If d2 < d1 Then
            reverse = True
        End If
    
    End If
    
    
    If reverse = False Then
        For i = 0 To size Step 2
            ret(index) = d(i)
            index = index + 1
            ret(index) = d(i + 1)
            index = index + 1
            
            'addDonut5 d(i), d(i + 1)
        Next
    
    Else
        For i = size - 1 To 0 Step -2
            ret(index) = d(i)
            index = index + 1
            ret(index) = d(i + 1)
            index = index + 1
            'addDonut5 d(i), d(i + 1)
        Next
    
    End If
    

End Function


Public Function getMerged() As Double()


    getMerged = ret

End Function


Public Function merge(d1() As Double, d2() As Double, d3() As Double) As Double()

    Dim size1 As Integer
    Dim size2 As Integer
    Dim size3 As Integer
    
    
    size1 = UBound(d1)
    size2 = UBound(d2)
    size3 = UBound(d3)
    
    
    ReDim ret(0 To size1 + size2 + size3 + 2) As Double
    
    
    idx = 0
    For i = 0 To size1 Step 2
        ret(idx) = d1(i)
        idx = idx + 1
        ret(idx) = d1(i + 1)
        idx = idx + 1
        
        addDonut5 d1(i), d1(i + 1)
    Next
    
    
    
    
    For i = 0 To size2 Step 2
        ret(idx) = d2(i)
        idx = idx + 1
        ret(idx) = d2(i + 1)
        idx = idx + 1
        
        addDonut5 d2(i), d2(i + 1)
        
        
    Next
    
    For i = 0 To size3 Step 2
        ret(idx) = d3(i)
        idx = idx + 1
        ret(idx) = d3(i + 1)
        idx = idx + 1
        
        addDonut5 d3(i), d3(i + 1)
    Next
    
    
    merge = ret
    


End Function

Attribute VB_Name = "ClsSelEntity"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Const VK_ESCAPE = &H1B, VK_ENTER = &HD, VK_LBUTTON = &H1
'Declare PtrSafe Function GetAsyncKeyState Lib "user32" (ByVal vKey As Long) As Integer

Public ent As AcadEntity
Public pt As New clsPoint


Public Function selectPolyline(prompt As String)

    Dim v As Variant

   On Error GoTo errControl
    
Start:
    ThisDrawing.Utility.getEntity ent, v, prompt
    
    
    
    
errControl:
    
    If Err.Description = "Method 'GetEntity' of object 'IAcadUtility' failed" Then
    
        If CheckKey(VK_ESCAPE) = True Or CheckKey(VK_ENTER) Then
            Debug.Print "End"
        
            End
        Else
            Debug.Print "Resume"
            Resume
        End If
    Else
    
        pt.x = v(0)
        pt.y = v(1)
    
        Debug.Print ""
        
        
        
    End If
    

End Function



Public Function getEntity()

    Set getEntity = ent

End Function


Public Function getPoint()

    Set getPoint = pt

End Function

Attribute VB_Name = "ClsSelReal"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False



Public Function selectReal()

    Dim rad As Double

    On Error GoTo errControl

    rad = getDefaultFilletRadius
    rad = ThisDrawing.Utility.GetReal("Radius (default: " & rad & ")   ")
    
    setDefaultFilletRadius rad
    
errControl:
    
    If Err.Description = "User input is a keyword" Then
        rad = getDefaultFilletRadius
    Else
    
    End If
    

    selectReal = rad

End Function


Public Function selectFilletRadius()

    Dim rad As Double

    On Error GoTo errControl

    rad = getDefaultFilletRadius
    rad = ThisDrawing.Utility.GetReal("Radius (default: " & rad & ")   ")
    
    setDefaultFilletRadius rad
    
errControl:
    
    If Err.Description = "User input is a keyword" Then
        rad = getDefaultFilletRadius
    Else
    
    End If
    

    selectFilletRadius = rad

End Function


Public Function selectChamferDistance()

    Dim dist As Double

    On Error GoTo errControl

    dist = getDefaultChamferDistance
    dist = ThisDrawing.Utility.GetReal("Distance (default: " & dist & ")   ")
    
    setDefaultChamferDistance dist
    
errControl:
    
    If Err.Description = "User input is a keyword" Then
        dist = getDefaultChamferDistance
        
    Else
    
    End If
    

    selectChamferDistance = dist

End Function

Attribute VB_Name = "CreateCircle"

Private Const PI As Double = 3.14159265358979
Private Const PI_2 As Double = 1.5707963267949


Sub Createcircle()
    Dim i, ii, x, y As Integer
    Dim FilterType(0) As Integer
    Dim FilterData(0) As Variant
    Dim UsersSelection As AcadSelectionSet
    Dim selObj() As AcadEntity
    Dim ret As Integer
    Dim arcObjs() As AcadEntity
    Dim ddd() As Double
    Dim x2, y2 As Variant
    Dim count As Integer
    Dim newv(0 To 1) As Double
    Dim centerPoint(0 To 2) As Double
    
    Dim returnObj1 As AcadObject
    Dim returnObj3 As AcadObject
    
    With ThisDrawing
        On Error Resume Next
        .SelectionSets("CurrentSelection").Delete
        Set UsersSelection = .SelectionSets.add("CurrentSelece e tion")
        
        
        'ThisDrawing.SetVariable "osmode", 512
        'p1 = ThisDrawing.Utility.GetPoint(, "Enter a point1: ")
        'ThisDrawing.SetVariable "osmode", 0
        'p2 = ThisDrawing.Utility.GetPoint(, "Enter a point2: ")
        'ThisDrawing.SetVariable "osmode", 512
        'p3 = ThisDrawing.Utility.GetPoint(, "Enter a point3: ")
        
        ThisDrawing.SetVariable "osmode", 512
        ThisDrawing.Utility.getEntity returnObj1, p1, "Enter a point 1: "
            
        ThisDrawing.SetVariable "osmode", 1
        p2 = ThisDrawing.Utility.getPoint(, "Enter a point2: ")
        
        ThisDrawing.SetVariable "osmode", 512
        ThisDrawing.Utility.getEntity returnObj3, p3, "Enter a point 3: "
        
        x1 = p1(0)
        y1 = p1(1)
        
        x2 = p2(0)
        y2 = p2(1)
         
        x3 = p3(0)
        y3 = p3(1)
        
        d1 = (x2 - x1) / (y2 - y1)
        d2 = (x3 - x2) / (y3 - y2)
        
        cx = ((y3 - y1) + (x2 + x3) * d2 - (x1 + x2) * d1) / (2 * (d2 - d1))
        cy = -d1 * (cx - (x1 + x2) / 2) + (y1 + y2) / 2
         
        r = VBA.Sqr((x1 - cx) ^ 2 + (y1 - cy) ^ 2)
        
        centerPoint(0) = cx
        centerPoint(1) = cy
        
        ThisDrawing.ModelSpace.AddCircle p1, 0.2
        
        'StartAngle = 10 * 3.14 / 180#
        'EndAngle = 230 * 3.14 / 180#
        
        'StartAngle = getAngle(cx + r, cy, x1, y1)
        'EngAngle = getAngle(cx + r, cy, x3, y3)
        
        'StartAngle = Excel.WorksheetFunction.Atan2((x1 - cx), (y1 - cy))
        'EndAngle = Excel.WorksheetFunction.Atan2((x3 - cx), (y3 - cy))
        
        StartAngle = ArcTan2((x1 - cx), (y1 - cy))
        EndAngle = ArcTan2((x3 - cx), (y3 - cy))
        
        
        
        If StartAngle > 0 And EndAngle > 0 Then
            If StartAngle > EndAngle Then
                tmp = StartAngle
                StartAngle = EndAngle
                EndAngle = tmp
            End If
        ElseIf StartAngle < 0 And EndAngle < 0 Then
            If StartAngle > EndAngle Then
                tmp = StartAngle
                StartAngle = EndAngle
                EndAngle = tmp
            End If
        ElseIf StartAngle > 0 And EndAngle < 0 Then
            If StartAngle < PI_2 Then
                tmp = StartAngle
                StartAngle = EndAngle
                EndAngle = tmp
            End If
        ElseIf StartAngle < 0 And EndAngle > 0 Then
            If EndAngle > PI_2 Then
                tmp = StartAngle
                StartAngle = EndAngle
                EndAngle = tmp
            End If
                
        End If
        
        
        
        ThisDrawing.ModelSpace.AddArc centerPoint, r, StartAngle, EndAngle
        
        
        'ThisDrawing.ModelSpace.AddCircle centerPoint, r
         
         
    End With
    
End Sub


   
Function ArcTan2(ByVal x As Double, ByVal y As Double) As Double


    Select Case x
        Case Is > 0
            ArcTan2 = Atn(y / x)
        Case Is < 0
            ArcTan2 = Atn(y / x) + PI * Sgn(y)
            If y = 0 Then ArcTan2 = ArcTan2 + PI
        Case Is = 0
            ArcTan2 = PI_2 * Sgn(y)
    End Select

End Function

Public Function Atn2(ByVal y As Double, ByVal x As Double) As Double

  If x > 0 Then

    Atn2 = Atn(y / x)

  ElseIf x < 0 Then

    Atn2 = Sgn(y) * (PI - Atn(Abs(y / x)))

  ElseIf y = 0 Then

    Atn2 = 0

  Else

    Atn2 = Sgn(y) * PI / 2

  End If

End Function

 


Function getEntitySize(ss As AcadSelectionSet, text As String) As Integer

    Dim count As Integer
    
    count = 0

    For Each ent In ss
        If ent.ObjectName = text Then
            count = count + 1
        End If
    Next ent
        
    getEntitySize = count
        


End Function

Attribute VB_Name = "Excutor"
Sub createFillet()

    Dim fillet As New clsFillet
    
    
    fillet.load
    
     

End Sub


Sub createFillet2()
    
    

    Dim fillet2 As New ClsFillet2
    
    
    fillet2.load
    
    

End Sub




Sub createFilletT()

    Dim filletT As New ClsFilletT
    
    
    filletT.load
    
    

End Sub



Sub createChamfer2()

    Dim chamfer2 As New clsChamfer2
    
    
    chamfer2.load
     
    

End Sub

Attribute VB_Name = "ModInit"
Public Const SHOW_CIRCLE = False

Public Const P2P_TOL = 100    ' 1~100: 1 ------100 민감
Public Const PD_TOL = 0.1     ' 0.1~1: 민감 0.1 ------ 1

Public Const KEY_TOL = "userr1"
Public Const KEY_RAD = "userr2"
Public Const KEY_CHA = "userr3"
Public Const DEF_TOL = 0.1
Public Const DEF_RAD = 3
Public Const DEF_CHA = 3

Public Function initConstant()

    Dim tol As Double
    Dim rad As Double
    
    tol = ThisDrawing.GetVariable(KEY_TOL)
    rad = ThisDrawing.GetVariable(KEY_RAD)


    If tol = 0 Then
        tol = DEF_TOL
        ThisDrawing.SetVariable KEY_TOL, tol
    End If


    If rad = 0 Then
        rad = DEF_RAD
        ThisDrawing.SetVariable KEY_RAD, rad
    End If


End Function


Public Function setDefaultFilletRadius(rad As Double)

    ThisDrawing.SetVariable KEY_RAD, rad

End Function

Public Function getDefaultFilletRadius() As Double

    Dim rad As Double
    rad = ThisDrawing.GetVariable(KEY_RAD)
    
    If rad = 0 Then
        rad = DEF_RAD
        ThisDrawing.SetVariable KEY_RAD, rad
    End If
    
    getDefaultFilletRadius = rad
    
End Function


Public Function setDefaultTolerance(tol As Double)

    ThisDrawing.SetVariable KEY_TOL, tol

End Function


Public Function getDefaultTolerance()

    Dim tol As Double
    tol = ThisDrawing.GetVariable(KEY_TOL)
   
    If tol = 0 Then
        tol = DEF_TOL
        ThisDrawing.SetVariable KEY_TOL, tol
    End If

    getDefaultTolerance = tol
    
End Function


Public Function setDefaultChamferDistance(cd As Double)

    ThisDrawing.SetVariable KEY_CHA, cd

End Function


Public Function getDefaultChamferDistance()

    Dim cd As Double
    cd = ThisDrawing.GetVariable(KEY_CHA)
   
    If cd = 0 Then
        cd = DEF_CHA
        ThisDrawing.SetVariable KEY_CHA, cd
    End If

    getDefaultChamferDistance = cd
    
End Function

Attribute VB_Name = "Module1"
Option Explicit
Function PolyCoords(oEnt As AcadEntity) As Variant
    Dim cnt As Integer
    Dim i As Integer
    Dim j As Integer
    Dim iStep As Integer
    Dim varPt As Variant
    Dim dblCoords() As Double
    Dim dblVert() As Double

    If TypeOf oEnt Is AcadLWPolyline Then
         iStep = 2
    ElseIf TypeOf oEnt Is Acad3DPolyline Or _
           TypeOf oEnt Is AcadPolyline Then
         iStep = 3
    End If
    dblCoords = oEnt.Coordinates

    ReDim ptsArr(0 To (UBound(dblCoords) + 1) \ iStep - 1, 0 To iStep - 1) As Double
    For i = 0 To (UBound(dblCoords) + 1) \ iStep - 1
         For j = 0 To iStep - 1
              ptsArr(i, j) = dblCoords(cnt)
              Debug.Print ptsArr(i, j)
              cnt = cnt + 1
         Next
    Next
    PolyCoords = ptsArr
End Function

Function Step2(pt1 As Variant) As Variant

    Dim UsersSelection As AcadSelectionSet
    Dim coord() As Double
    Dim sel As AcadEntity
    
    Dim ent As AcadEntity
    Dim plieObj As AcadPolyline
    

    Dim position(0 To 2) As Double
    With ThisDrawing
        On Error Resume Next
        .SelectionSets("CurrentSelection").Delete
        Set UsersSelection = .SelectionSets.add("CurrentSelection")
        UsersSelection.SelectAtPoint (pt1)
     
        Set sel = UsersSelection.Item(0)
        'sel.color = acBlue
        
        'createPolygon (sel.Coordinates)
            
        Set plieObj = ThisDrawing.ModelSpace.AddPolyline(sel.Coordinates)
        
        plieObj.color = arBlue
        
        MsgBox UsersSelection.Name
     
    End With
    
    
End Function


Function createPolygon(verlist As Double)

    Dim obj As AcadPolyline
    
    
    obj = ThisDrawing.ModelSpace.AddPolyline(verlist)
    obj.color = arBlue

End Function


Sub demo()
    Dim pts As Variant
    Dim varPt As Variant
    Dim oEnt As AcadEntity
    Dim returnPnt As Variant
    
    Dim returnObj1 As AcadObject
    Dim basePnt1 As Variant
    
    Dim returnObj2 As AcadObject
    Dim basePnt2 As Variant
    
    Dim startPoint(0 To 2) As Double
    Dim endPoint(0 To 2) As Double
    
    Dim plist() As Double
    
    ' Return a point using a prompt
    basePnt1 = ThisDrawing.Utility.getPoint(, "Enter a point1: ")
    basePnt2 = ThisDrawing.Utility.getPoint(, "Enter a point2: ")
    'ThisDrawing.Utility.GetEntity returnObj1, basePnt1, "enter a point1"
    'ThisDrawing.Utility.GetEntity returnObj2, basePnt2, "enter a point2"
    
    
    Step2 (basePnt1)
    ThisDrawing.ModelSpace.addLine basePnt1, basePnt2
    ThisDrawing.ModelSpace.add
    
    
    
    
   
    
    
    'pts = step(oEnt)
End Sub

Attribute VB_Name = "Module2"
Function Step2(pt1 As Variant) As Variant

    Dim UsersSelection As AcadSelectionSet
    Dim coord() As Double
    Dim sel As AcadEntity
    
    Dim ent As AcadEntity
    Dim plieObj As AcadPolyline
    

    Dim position(0 To 2) As Double
    With ThisDrawing
        On Error Resume Next
        .SelectionSets("CurrentSelection").Delete
        Set UsersSelection = .SelectionSets.add("CurrentSelection")
        UsersSelection.SelectAtPoint (pt1)
     
        Set sel = UsersSelection.Item(0)
        'sel.color = acBlue
        
        'createPolygon (sel.Coordinates)
            
        Set plieObj = ThisDrawing.ModelSpace.AddPolyline(sel.Coordinates)
        
        plieObj.color = arBlue
        
        MsgBox UsersSelection.Name
     
    End With
    
    
End Function


Sub arc2lines()

    Dim myArc As AcadArc
    Dim objSel As AcadEntity
    Dim myPL As AcadLWPolyline
    Dim mypolarpoint
    Dim Bulge() As Double
    Dim legs As Integer
    Const PI = 3.14159265358979
    Dim delta As Double
    
    ThisDrawing.Utility.getEntity objSel, returnObj, "Select Arc:"
    If objSel.ObjectName = "AcDbArc" Then
        Set myArc = objSel
        delta = myArc.EndAngle - myArc.StartAngle
        If delta < 0 Then delta = delta + (2 * PI)
        Dim numOfSegments As Integer
        Dim points() As Double
        'adjust below for reality
        numOfSegments = CInt(myArc.ArcLength) ' length of segment = 1, last segment = remainder
        ReDim points(0 To 2 * numOfSegments + 1)
        ang = 1 / myArc.Radius
        points(0) = myArc.startPoint(0)
        points(1) = myArc.startPoint(1)
        adir = ang
        For x = 2 To UBound(points) - 2 Step 2
            mypolarpoint = ThisDrawing.Utility.PolarPoint(myArc.Center, myArc.StartAngle + adir, myArc.Radius)
            adir = adir + ang
            points(x) = mypolarpoint(0)
            points(x + 1) = mypolarpoint(1)
        Next x
        points(UBound(points) - 1) = myArc.endPoint(0)
        points(UBound(points) - 0) = myArc.endPoint(1)
        Set myPL = ThisDrawing.ModelSpace.AddLightWeightPolyline(points)
        myPL.Update
    End If

End Sub

Attribute VB_Name = "Module3"
Sub Step1()
    Dim arcObjs() As AcadEntity
    Dim plroad() As AcadEntity
    Dim plObjs(0 To 1) As AcadEntity
    Dim ddd() As Double
    
    Dim ent As AcadEntity
    Dim ent2 As AcadEntity
    
    Dim vx, vy As Double
    Dim count As Integer
    
    Dim filletpoint(0 To 7) As Double   '8
    
    Dim dout1() As Double
    Dim dout2() As Double
    
    Dim df1() As Double
    Dim df2() As Double
    
    Dim dresult() As Double
    Dim plResult As AcadLWPolyline
    
    
    
    plroad = selectPolylineObs
    'arcObjs = selectArcObs
    'plObjs = arc2lines(arcObjs)
    
    
    Set plObjs(0) = addFilletArcline
    Set plObjs(1) = addFilletArcline()
    
    'ddd = plObjs(0).Coordinates
    
    index = 0
    For i = 0 To UBound(plroad)
        Set ent = plroad(i)
        
        For j = 0 To UBound(plObjs)
        
            Set ent2 = plObjs(j)    ' fillet 위치
            ddd = ent2.Coordinates
            
            count = UBound(ddd)
            
            vx = ddd(count - 1)
            vy = ddd(count)
            
            newp = addVertex(ent, vx, vy)
            
            If newp(0) <> 0 And newp(1) <> 0 Then
            
                filletpoint(index) = newp(0)
                index = index + 1
                filletpoint(index) = newp(1)
                index = index + 1
                 
            End If
            
            
            vx = ddd(0)
            vy = ddd(1)
        
            newp = addVertex(ent, vx, vy)
        
            If newp(0) <> 0 And newp(1) <> 0 Then
            
                filletpoint(index) = newp(0)
                index = index + 1
                filletpoint(index) = newp(1)
                index = index + 1
                 
            End If
        
        Next
    Next
    
    
    
    dout1 = searchOutLine(plroad(0), plObjs(0), plObjs(1))
    
    'ThisDrawing.ModelSpace.AddLightWeightPolyline(dout1).color = acRed
    
    dout2 = searchInnerLine(plroad(1), plObjs(0), plObjs(1))
    
    'ThisDrawing.ModelSpace.AddLightWeightPolyline(dout2).color = acMagenta
    
    Set ent = plObjs(0)
    df1 = ent.Coordinates
    Set ent = plObjs(1)
    df2 = ent.Coordinates
    
    dresult = mergeAll(dout1, df1, dout2, df2)
    
    
    Set plResult = ThisDrawing.ModelSpace.AddLightWeightPolyline(dresult)
    plResult.Closed = True
    plResult.Update
    
    plroad(0).Delete
    deleteEntities plObjs
    
End Sub


Function addFilletArcline()

    ThisDrawing.SetVariable "osmode", 512
    ThisDrawing.Utility.getEntity returnObj1, tmp, "Enter a point 1: "
        
    p1(0) = tmp(0)
    p1(1) = tmp(1)
        
    ThisDrawing.SetVariable "osmode", 0
    p2 = ThisDrawing.Utility.getPoint(, "Enter a point2: ")
     
    ThisDrawing.SetVariable "osmode", 512
    ThisDrawing.Utility.getEntity returnObj3, tmp, "Enter a point 3: "
    
    p3(0) = tmp(0)
    p3(1) = tmp(1)
    
    
    Set retArc = getArcBy3P(p1, p2, p3) '세점을 지나는 아크를 생성
    
    
    Set addFilletArcline = arc2line(retArc)  '아크를 라인으로 변경

End Function


Function deleteEntities(ents() As AcadEntity)

    Dim ent As AcadEntity
    
    For i = 0 To UBound(ents)
        Set ent = ents(i)
        ent.Delete
    Next
    
End Function





Function mergeAll(d1() As Double, d2() As Double, d3() As Double, d4() As Double) As Double()

    Dim dout() As Double
    Dim count As Integer
    Dim reverse As Boolean
    
    
    reverse = False
    
    'count = UBound(d1) + UBound(d2) + 3 - 2
    'count = UBound(d1) + UBound(d2) + UBound(d3) + 4 - 2
    count = UBound(d1) + UBound(d2) + UBound(d3) + UBound(d4) + 1 - 2
    
    ReDim dout(count) As Double
    
    idx = 0
    
    For i = 0 To UBound(d1)
        dout(idx) = d1(i)
        idx = idx + 1
    Next
    
    
    addDonut3 d1(0), d1(1)
    addDonut3 dout(idx - 2), dout(idx - 1)
    
    If d2(0) = d1(UBound(d1) - 1) Then
        reverse = False
    Else
        reverse = True
    End If
    
    If reverse = False Then
        For i = 2 To UBound(d2) Step 2
            dout(idx) = d2(i)
            idx = idx + 1
            dout(idx) = d2(i + 1)
            idx = idx + 1
            addDonut3 dout(idx - 2), dout(idx - 1)
        Next
        
    Else
        For i = UBound(d2) - 3 To 0 Step -2
            dout(idx) = d2(i)
            idx = idx + 1
            dout(idx) = d2(i + 1)
            idx = idx + 1
            addDonut3 dout(idx - 2), dout(idx - 1)
        Next
    End If
        
    If reverse = False Then
        For i = 2 To UBound(d3) Step 2
            dout(idx) = d3(i)
            idx = idx + 1
            dout(idx) = d3(i + 1)
            idx = idx + 1
            addDonut3 dout(idx - 2), dout(idx - 1)
     
        Next
    Else
        For i = UBound(d3) - 1 To 0 Step -2
            dout(idx) = d3(i)
            idx = idx + 1
            dout(idx) = d3(i + 1)
            idx = idx + 1
            addDonut3 dout(idx - 2), dout(idx - 1)
        Next
    End If
    
    If d3(0) = d2(UBound(d2) - 1) Then
        reverse = Not reverse
    Else
        reverse = reverse
    End If
    
    If reverse = True Then 'd3(0) = d2(UBound(d2) - 1)
        For i = 2 To UBound(d4) Step 2
            dout(idx) = d4(i)
            idx = idx + 1
            dout(idx) = d4(i + 1)
            idx = idx + 1
            addDonut3 dout(idx - 2), dout(idx - 1)
        Next
    Else
        For i = UBound(d4) - 1 To 0 Step -2
            dout(idx) = d4(i)
            idx = idx + 1
            dout(idx) = d4(i + 1)
            idx = idx + 1
            addDonut3 dout(idx - 2), dout(idx - 1)
        Next
    End If
    
     
    'addDonut3 d4(0), d4(1)
    'addDonut3 dout(idx - 2), dout(idx - 1)

    
    
    
    mergeAll = dout
    
    

End Function



Function searchInnerLine(plobj As AcadEntity, f1obj As AcadEntity, f2obj As AcadEntity) As Double()
    searchInnerLine = searchCrossLine(plobj, f1obj, f2obj, True)
End Function

Function searchOutLine(plobj As AcadEntity, f1obj As AcadEntity, f2obj As AcadEntity) As Double()

    searchOutLine = searchCrossLine(plobj, f1obj, f2obj, False)

End Function


Function searchCrossLine(plobj As AcadEntity, f1obj As AcadEntity, f2obj As AcadEntity, isinner As Boolean) As Double()

    Dim dpl() As Double
    Dim df1() As Double
    Dim df2() As Double
    Dim point As Double
    
    Dim f1idx, f1idxn As Integer    '필렛1 접점 인덱스
    Dim f2idx, f2idxn As Integer    '필렛2 접점 인덱스
    
    Dim index1, index1n As Integer   '폴리라인 접점 인덱스
    
    
    Dim dret() As Double    '리턴좌표
    Dim itotal As Integer
    
    'Set ret = Nothing
    
    dpl = plobj.Coordinates '폴리라인
    df1 = f1obj.Coordinates '필렛1
    df2 = f2obj.Coordinates '필렛2

    x = df1(0)
    y = df1(1)
    
    
    index1 = searchIndex(dpl, x, y)
    
    If index1 = -1 Then
        count = UBound(df1)
        
        x = df1(count - 1)
        y = df1(count)
        
        index1 = searchIndex(dpl, x, y)
        f1idx = count - 1
        f1idxn = count - 3
    Else
        f1idx = 0
        f1idxn = 2
        
    
    End If
    
    x = df2(0)
    y = df2(1)
    
    index2 = searchIndex(dpl, x, y)
    
    If index2 = -1 Then
        count = UBound(df2)
        
        x = df2(count - 1)
        y = df2(count)
        
        index2 = searchIndex(dpl, x, y)
        f2idx = count - 1
        f2idxn = count - 3
    Else
        f2idx = 0
        f2idxn = 2
    End If
    


    If index1 + 2 > UBound(dpl) Then
        index1n = index1 - 2
    Else
        index1n = index1 + 2
    End If


    cx = dpl(index1)
    cy = dpl(index1 + 1)
    
    x1 = dpl(index1n)
    y1 = dpl(index1n + 1)
    
    x2 = df1(f1idxn)
    y2 = df1(f1idxn + 1)

    'addDonut3 cx, cy
    'addDonut3 x1, y1
    'addDonut3 x2, y2
    


    rad = Abs(Atn((y2 - cy) / (x2 - cx)) - Atn((y1 - cy) / (c1 - cx)))
    
    
    
    If (rad < 1.571) = isinner Then '삭제영역에 해당함
    
        itotal = UBound(dpl)
        If index2 = 0 Then
            index2 = itotal
        End If
        
        If index2 > index1 Then     '올바른 방향임
            count = index2 - index1 + 2
            ReDim dret(0 To count) As Double
            
            idx = 0
            
            For i = index1 To index2 + 2 Step 2
            
                If i > itotal Then
                    dret(idx) = dpl(i - (itotal + 1))
                    idx = idx + 1
                    dret(idx) = dpl(i - (itotal + 1) + 1)
                    idx = idx + 1
                Else
                    dret(idx) = dpl(i)
                    idx = idx + 1
                    dret(idx) = dpl(i + 1)
                    idx = idx + 1
                End If
            
                'addDonut3 dret(idx - 2), dret(idx - 1)
            Next
        
        Else
            count = index1 - index2 + 1
            ReDim dret(0 To count) As Double
            
            idx = 0
            
            For i = index2 To index1 + 1 Step 2
                dret(idx) = dpl(i)
                idx = idx + 1
                dret(idx) = dpl(i + 1)
                idx = idx + 1
            Next
            'count = index1 - index2 + 1
            'ReDim dret(0 To count) As Double
            
            'idx = 0
            'For i = index1 To index2 Step -2
            '   dret(idx) = dpl(i)
            '   idx = idx + 1
            '   dret(idx) = dpl(i + 1)
            '   idx = idx + 1
            '   addDonut3 dpl(i), dpl(i + 1)
            
            'Next
        
            Debug.Print " "
            
        
        End If
        
    Else
        If index2 > index1 Then
        
            count = index1 + UBound(dpl) - index2 + 2   'y좌표 2개라서 +2
            ReDim dret(0 To count) As Double
            idx = 0
        
            For i = index2 To UBound(dpl)   '개수만큼 찾기때문에 y가 포함됨 +1 안함
                dret(idx) = dpl(i)
                idx = idx + 1
            Next
                    
            For i = 0 To index1 + 1 'y좌표 포함해야하므로 +1
                dret(idx) = dpl(i)
                idx = idx + 1
            Next
            
            
            Debug.Print
            
            
            
        Else
        
        End If
    
    End If
    
    
    
    searchCrossLine = dret
    

End Function

Function searchIndex(d() As Double, ByVal x As Double, ByVal y As Double) As Integer

    Dim index As Integer
    
    index = -1
    
    For i = 0 To UBound(d) Step 2
    
        If d(i) = x And d(i + 1) = y Then
            index = i
        End If
    
    Next


    searchIndex = index
    
End Function


 



 

Sub SelectRawData()
    Dim i, ii, x, y As Integer
    Dim FilterType(0) As Integer
    Dim FilterData(0) As Variant
    Dim UsersSelection As AcadSelectionSet
    Dim selObj() As AcadEntity
    Dim ret As Integer
    Dim arcObjs() As AcadEntity
    Dim ddd() As Doubleos
    Dim x2, y2 As Variant
    Dim count As Integer
    Dim newv(0 To 1) As Double
    
    ThisDrawing.SetVariable "osmode", 512
    
    With ThisDrawing
        On Error Resume Next
        .SelectionSets("CurrentSelection").Delete
        Set UsersSelection = .SelectionSets.add("CurrentSelection")
        
        
        FilterType(0) = 0
        FilterData(0) = "LWPolyline"
        
        UsersSelection.SelectOnScreen FilterType, FilterData
        
        
        count = getEntitySize(UsersSelection, "AcDbPolyline") - 1 'AcDbArc
        
        ReDim selObj(0 To count) As AcadEntity
        
        For i = 0 To count
            Set selObj(i) = UsersSelection.Item(i)
            Debug.Print " "
             
        Next i
        
        
    End With
    
    
    vx = 1194.35534891423
    vy = 2999.85414787302
    newv(0) = vx: newv(1) = vy
    
    For i = 0 To count
        ddd = selObj(i).Coordinates
        count = UBound(ddd)
        
        x1 = ddd(count - 1)
        y1 = ddd(count)
        
        For ii = 0 To count Step 2
        
            x2 = ddd(ii)
            y2 = ddd(ii + 1)
            
            f = (y2 - y1) / (x2 - x1)
            
            f1 = (vy - y1) / (vx - x1)
            f2 = (y2 - vy) / (x2 - vx)
            
            If Abs(f1 - f2) < 0.00001 Then
                addDonut x2, y2
                addDonut x1, y1
                
                selObj(i).addVertex ii / 2, newv
                selObj(i).Update
            
            End If
            
            x1 = x2
            y1 = y2
            
        Next ii
    Next i
    
    
    
    Debug.Print " "
    
    
End Sub





Function getArcSize(ss As AcadSelectionSet) As Integer

    Dim count As Integer

    count = 0

    For Each ent In ss
        If ent.ObjectName = "AcDbArc" Then
            count = count + 1
        End If
    Next ent
        
    getArcSize = count
        


End Function


Function arc2lines(arcs() As AcadEntity) As AcadEntity()

    Dim i As Integer
    Dim myArc As AcadArc
    Dim objSel As AcadEntity
    Dim myPL As AcadLWPolyline
    Dim mypolarpoint
    Dim Bulge() As Double
    Dim legs As Integer
    Const PI = 3.14159265358979
    Dim delta As Double
    Dim count As Integer
    Dim retObj() As AcadEntity
    
    count = UBound(arcs)
    ReDim retObj(0 To count) As AcadEntity
        
    For i = 0 To UBound(arcs)
        Set myArc = arcs(i)
 
        delta = myArc.EndAngle - myArc.StartAngle
        If delta < 0 Then delta = delta + (2 * PI)
        Dim numOfSegments As Integer
        Dim points() As Double
        'adjust below for reality
        numOfSegments = CInt(myArc.ArcLength) ' length of segment = 1, last segment = remainder
        ReDim points(0 To 2 * numOfSegments + 1)
        ang = 1 / myArc.Radius
        points(0) = myArc.startPoint(0)
        points(1) = myArc.startPoint(1)
        adir = ang
        For x = 2 To UBound(points) - 2 Step 2
            mypolarpoint = ThisDrawing.Utility.PolarPoint(myArc.Center, myArc.StartAngle + adir, myArc.Radius)
            adir = adir + ang
            points(x) = mypolarpoint(0)
            points(x + 1) = mypolarpoint(1)
        Next x
        points(UBound(points) - 1) = myArc.endPoint(0)
        points(UBound(points) - 0) = myArc.endPoint(1)
        Set retObj(i) = ThisDrawing.ModelSpace.AddLightWeightPolyline(points)
        retObj(i).Update
        
       
        
        myArc.Delete
        
    Next i
    
    arc2lines = retObj

End Function
 


Sub test()
    
    Dim SelPl(0 To 1) As AcadEntity
    Dim splyObj As AcadLWPolyline
    Dim newObj As AcadLWPolyline
    
    
    Dim UsersSelection As AcadSelectionSet
    
    
    Dim DrawingSelected As AcadEntity 'delete the selection set if it already exists
    Dim intPoint12 As Variant
    Dim FilterType(0) As Integer
    Dim FilterData(0) As Variant
    Dim splyCoords() As Double
    
    Dim temp As Variant
    
    Dim index As Integer
    
    
    With ThisDrawing
        On Error Resume Next
        .SelectionSets("CurrentSelection").Delete
        'get selection from user
        MsgBox "Select objects! Hit Enter to finish!"
        Set UsersSelection = .SelectionSets.add("CurrentSelection")
        
        FilterType(0) = 0
        FilterData(0) = "LWPolyline"
        
        UsersSelection.SelectOnScreen FilterType, FilterData
        Set SelPl(0) = UsersSelection.Item(0)
        Set SelPl(1) = UsersSelection.Item(1)
        
        intPoint12 = SelPl(0).IntersectWith(SelPl(1), acExtendNone)
         
        
        splyCoords = SelPl(0).Coordinates
        splyCoords(7) = 2000
        
        SelPl(0).Update
        
        
        Set newObj = ThisDrawing.ModelSpace.AddLightWeightPolyline(splyCoords)
        newObj.Closed = True
        
        
        Debug.Print " "
        
        
    End With

End Sub

Attribute VB_Name = "Module4"
Sub Step2()
    Dim dstPL As AcadEntity
    Dim srcPL As AcadEntity
    Dim flPL As AcadEntity
    Dim ddd() As Double
    
    Dim ent As AcadEntity
    Dim ent2 As AcadEntity
    
    Dim vx, vy As Double
    Dim count As Integer
    
    Dim filletpoint(0 To 7) As Double   '8
    
    Dim dout1() As Double
    Dim dout2() As Double
    
    Dim df1() As Double
    Dim df2() As Double
    
    Dim dresult() As Double
    Dim plResult As AcadLWPolyline
    
    Dim p1(0 To 2) As Double
    Dim p3(0 To 2) As Double
    Dim p4(0 To 2) As Double
    
    With ThisDrawing
        On Error Resume Next
        .SelectionSets("CurrentSelection").Delete
        Set UsersSelection = .SelectionSets.add("CurrentSelection")
        
        ThisDrawing.SetVariable "osmode", 512
        ThisDrawing.Utility.getEntity dstPL, p1, "Enter a point 1: "
            
        ThisDrawing.SetVariable "osmode", 1
        p2 = ThisDrawing.Utility.getPoint(, "Enter a point2: ")
        
        ThisDrawing.SetVariable "osmode", 512
        ThisDrawing.Utility.getEntity srcPL, p3, "Enter a point 3: "
    End With
    
    
       
    plObjs = arc2lines(arcObjs)
    'ddd = plObjs(0).Coordinates
    
    index = 0
    For i = 0 To UBound(plroad)
        Set ent = plroad(i)
        
        For j = 0 To UBound(plObjs)
        
            Set ent2 = plObjs(j)    ' fillet 위치
            ddd = ent2.Coordinates
            
            count = UBound(ddd)
            
            vx = ddd(count - 1)
            vy = ddd(count)
            
            newp = addVertex(ent, vx, vy)
            
            If newp(0) <> 0 And newp(1) <> 0 Then
            
                filletpoint(index) = newp(0)
                index = index + 1
                filletpoint(index) = newp(1)
                index = index + 1
                 
            End If
            
            
            vx = ddd(0)
            vy = ddd(1)
        
            newp = addVertex(ent, vx, vy)
        
            If newp(0) <> 0 And newp(1) <> 0 Then
            
                filletpoint(index) = newp(0)
                index = index + 1
                filletpoint(index) = newp(1)
                index = index + 1
                 
            End If
        
        Next
    Next
    
    
    
    dout1 = searchOutLine(plroad(0), plObjs(0), plObjs(1))
    
    'ThisDrawing.ModelSpace.AddLightWeightPolyline(dout1).color = acRed
    
    dout2 = searchInnerLine(plroad(1), plObjs(0), plObjs(1))
    
    'ThisDrawing.ModelSpace.AddLightWeightPolyline(dout2).color = acMagenta
    
    Set ent = plObjs(0)
    df1 = ent.Coordinates
    Set ent = plObjs(1)
    df2 = ent.Coordinates
    
    dresult = mergeAll(dout1, df1, dout2, df2)
    
    
    Set plResult = ThisDrawing.ModelSpace.AddLightWeightPolyline(dresult)
    plResult.Closed = True
    plResult.Update
    
    plroad(0).Delete
    deleteEntities plObjs
    
End Sub


Function deleteEntities(ents() As AcadEntity)

    Dim ent As AcadEntity
    
    For i = 0 To UBound(ents)
        Set ent = ents(i)
        ent.Delete
    Next
    
End Function





Function mergeAll(d1() As Double, d2() As Double, d3() As Double, d4() As Double) As Double()

    Dim dout() As Double
    Dim count As Integer
    Dim reverse As Boolean
    
    
    reverse = False
    
    'count = UBound(d1) + UBound(d2) + 3 - 2
    'count = UBound(d1) + UBound(d2) + UBound(d3) + 4 - 2
    count = UBound(d1) + UBound(d2) + UBound(d3) + UBound(d4) + 3 - 2
    
    ReDim dout(count) As Double
    
    idx = 0
    
    For i = 0 To UBound(d1)
        dout(idx) = d1(i)
        idx = idx + 1
    Next
    
    
    addDonut3 d1(0), d1(1)
    addDonut3 dout(idx - 2), dout(idx - 1)
    
    If d2(0) = d1(UBound(d1) - 1) Then
        reverse = False
    Else
        reverse = True
    End If
    
    If reverse = False Then
        For i = 2 To UBound(d2) Step 2
            dout(idx) = d2(i)
            idx = idx + 1
            dout(idx) = d2(i + 1)
            idx = idx + 1
            addDonut3 dout(idx - 2), dout(idx - 1)
        Next
        
    Else
        For i = UBound(d2) - 3 To 0 Step -2
            dout(idx) = d2(i)
            idx = idx + 1
            dout(idx) = d2(i + 1)
            idx = idx + 1
            addDonut3 dout(idx - 2), dout(idx - 1)
        Next
    End If
        
    If reverse = False Then
        For i = 2 To UBound(d3) Step 2
            dout(idx) = d3(i)
            idx = idx + 1
            dout(idx) = d3(i + 1)
            idx = idx + 1
            addDonut3 dout(idx - 2), dout(idx - 1)
     
        Next
    Else
        For i = UBound(d3) - 1 To 0 Step -2
            dout(idx) = d3(i)
            idx = idx + 1
            dout(idx) = d3(i + 1)
            idx = idx + 1
            addDonut3 dout(idx - 2), dout(idx - 1)
        Next
    End If
    
    If d3(0) = d2(UBound(d2) - 1) Then
        reverse = reverse
    Else
        reverse = Not reverse
    End If
    
    If reverse = True Then 'd3(0) = d2(UBound(d2) - 1)
        For i = 2 To UBound(d4) Step 2
            dout(idx) = d4(i)
            idx = idx + 1
            dout(idx) = d4(i + 1)
            idx = idx + 1
            addDonut3 dout(idx - 2), dout(idx - 1)
        Next
    Else
        For i = UBound(d4) - 1 To 0 Step -2
            dout(idx) = d4(i)
            idx = idx + 1
            dout(idx) = d4(i + 1)
            idx = idx + 1
            addDonut3 dout(idx - 2), dout(idx - 1)
        Next
    End If
    
     
    'addDonut3 d4(0), d4(1)
    'addDonut3 dout(idx - 2), dout(idx - 1)

    
    
    
    mergeAll = dout
    
    

End Function



Function searchInnerLine(plobj As AcadEntity, f1obj As AcadEntity, f2obj As AcadEntity) As Double()
    searchInnerLine = searchCrossLine(plobj, f1obj, f2obj, True)
End Function

Function searchOutLine(plobj As AcadEntity, f1obj As AcadEntity, f2obj As AcadEntity) As Double()

    searchOutLine = searchCrossLine(plobj, f1obj, f2obj, False)

End Function


Function searchCrossLine(plobj As AcadEntity, f1obj As AcadEntity, f2obj As AcadEntity, isinner As Boolean) As Double()

    Dim dpl() As Double
    Dim df1() As Double
    Dim df2() As Double
    Dim point As Double
    
    Dim f1idx, f1idxn As Integer    '필렛1 접점 인덱스
    Dim f2idx, f2idxn As Integer    '필렛2 접점 인덱스
    
    Dim index1, index1n As Integer   '폴리라인 접점 인덱스
    
    
    Dim dret() As Double    '리턴좌표
    Dim itotal As Integer
    
    'Set ret = Nothing
    
    dpl = plobj.Coordinates '폴리라인
    df1 = f1obj.Coordinates '필렛1
    df2 = f2obj.Coordinates '필렛2

    x = df1(0)
    y = df1(1)
    
    
    index1 = searchIndex(dpl, x, y)
    
    If index1 = -1 Then
        count = UBound(df1)
        
        x = df1(count - 1)
        y = df1(count)
        
        index1 = searchIndex(dpl, x, y)
        f1idx = count - 1
        f1idxn = count - 3
    Else
        f1idx = 0
        f1idxn = 2
        
    
    End If
    
    x = df2(0)
    y = df2(1)
    
    index2 = searchIndex(dpl, x, y)
    
    If index2 = -1 Then
        count = UBound(df2)
        
        x = df2(count - 1)
        y = df2(count)
        
        index2 = searchIndex(dpl, x, y)
        f2idx = count - 1
        f2idxn = count - 3
    Else
        f2idx = 0
        f2idxn = 2
    End If
    


    If index1 + 2 > UBound(dpl) Then
        index1n = index1 - 2
    Else
        index1n = index1 + 2
    End If


    cx = dpl(index1)
    cy = dpl(index1 + 1)
    
    x1 = dpl(index1n)
    y1 = dpl(index1n + 1)
    
    x2 = df1(f1idxn)
    y2 = df1(f1idxn + 1)

    'addDonut3 cx, cy
    'addDonut3 x1, y1
    'addDonut3 x2, y2
    


    rad = Abs(Atn((y2 - cy) / (x2 - cx)) - Atn((y1 - cy) / (c1 - cx)))
    
    
    
    If (rad < 1.571) = isinner Then '삭제영역에 해당함
    
        itotal = UBound(dpl)
        If index2 = 0 Then
            index2 = itotal
        End If
        
        If index2 > index1 Then     '올바른 방향임
            count = index2 - index1 + 2
            ReDim dret(0 To count) As Double
            
            idx = 0
            
            For i = index1 To index2 + 2 Step 2
            
                If i > itotal Then
                    dret(idx) = dpl(i - (itotal + 1))
                    idx = idx + 1
                    dret(idx) = dpl(i - (itotal + 1) + 1)
                    idx = idx + 1
                Else
                    dret(idx) = dpl(i)
                    idx = idx + 1
                    dret(idx) = dpl(i + 1)
                    idx = idx + 1
                End If
            
                'addDonut3 dret(idx - 2), dret(idx - 1)
            Next
        
        Else
            count = index1 - index2 + 1
            ReDim dret(0 To count) As Double
            
            idx = 0
            
            For i = index2 To index1 + 1 Step 2
                dret(idx) = dpl(i)
                idx = idx + 1
                dret(idx) = dpl(i + 1)
                idx = idx + 1
            Next
            'count = index1 - index2 + 1
            'ReDim dret(0 To count) As Double
            
            'idx = 0
            'For i = index1 To index2 Step -2
            '   dret(idx) = dpl(i)
            '   idx = idx + 1
            '   dret(idx) = dpl(i + 1)
            '   idx = idx + 1
            '   addDonut3 dpl(i), dpl(i + 1)
            
            'Next
        
            Debug.Print " "
            
        
        End If
        
    Else
        If index2 > index1 Then
        
            count = index1 + UBound(dpl) - index2 + 2   'y좌표 2개라서 +2
            ReDim dret(0 To count) As Double
            idx = 0
        
            For i = index2 To UBound(dpl)   '개수만큼 찾기때문에 y가 포함됨 +1 안함
                dret(idx) = dpl(i)
                idx = idx + 1
            Next
                    
            For i = 0 To index1 + 1 'y좌표 포함해야하므로 +1
                dret(idx) = dpl(i)
                idx = idx + 1
            Next
            
            
            Debug.Print
            
            
            
        Else
        
        End If
    
    End If
    
    
    
    searchCrossLine = dret
    

End Function

Function searchIndex(d() As Double, ByVal x As Double, ByVal y As Double) As Integer

    Dim index As Integer
    
    index = -1
    
    For i = 0 To UBound(d) Step 2
    
        If d(i) = x And d(i + 1) = y Then
            index = i
        End If
    
    Next


    searchIndex = index
    
End Function


 

 

Sub SelectRawData()
    Dim i, ii, x, y As Integer
    Dim FilterType(0) As Integer
    Dim FilterData(0) As Variant
    Dim UsersSelection As AcadSelectionSet
    Dim selObj() As AcadEntity
    Dim ret As Integer
    Dim arcObjs() As AcadEntity
    Dim ddd() As Double
    Dim x2, y2 As Variant
    Dim count As Integer
    Dim newv(0 To 1) As Double
    
    
    With ThisDrawing
        On Error Resume Next
        .SelectionSets("CurrentSelection").Delete
        Set UsersSelection = .SelectionSets.add("CurrentSelection")
        
        
        FilterType(0) = 0
        FilterData(0) = "LWPolyline"
        
        UsersSelection.SelectOnScreen FilterType, FilterData
        
        
        count = getEntitySize(UsersSelection, "AcDbPolyline") - 1 'AcDbArc
        
        ReDim selObj(0 To count) As AcadEntity
        
        For i = 0 To count
            Set selObj(i) = UsersSelection.Item(i)
            Debug.Print " "
             
        Next i
        
        
    End With
    
    
    vx = 1194.35534891423
    vy = 2999.85414787302
    newv(0) = vx: newv(1) = vy
    
    For i = 0 To count
        ddd = selObj(i).Coordinates
        count = UBound(ddd)
        
        x1 = ddd(count - 1)
        y1 = ddd(count)
        
        For ii = 0 To count Step 2
        
            x2 = ddd(ii)
            y2 = ddd(ii + 1)
            
            f = (y2 - y1) / (x2 - x1)
            
            f1 = (vy - y1) / (vx - x1)
            f2 = (y2 - vy) / (x2 - vx)
            
            If Abs(f1 - f2) < 0.00001 Then
                addDonut x2, y2
                addDonut x1, y1
                
                selObj(i).addVertex ii / 2, newv
                selObj(i).Update
            
            End If
            
            x1 = x2
            y1 = y2
            
        Next ii
    Next i
    
    
    
    Debug.Print " "
    
    
End Sub
 
 

Function getArcSize(ss As AcadSelectionSet) As Integer

    Dim count As Integer

    count = 0

    For Each ent In ss
        If ent.ObjectName = "AcDbArc" Then
            count = count + 1
        End If
    Next ent
        
    getArcSize = count
        


End Function


Function arc2lines(arcs() As AcadEntity) As AcadEntity()

    Dim i As Integer
    Dim myArc As AcadArc
    Dim objSel As AcadEntity
    Dim myPL As AcadLWPolyline
    Dim mypolarpoint
    Dim Bulge() As Double
    Dim legs As Integer
    Const PI = 3.14159265358979
    Dim delta As Double
    Dim count As Integer
    Dim retObj() As AcadEntity
    
    count = UBound(arcs)
    ReDim retObj(0 To count) As AcadEntity
        
    For i = 0 To UBound(arcs)
        Set myArc = arcs(i)
 
        delta = myArc.EndAngle - myArc.StartAngle
        If delta < 0 Then delta = delta + (2 * PI)
        Dim numOfSegments As Integer
        Dim points() As Double
        'adjust below for reality
        numOfSegments = CInt(myArc.ArcLength) ' length of segment = 1, last segment = remainder
        ReDim points(0 To 2 * numOfSegments + 1)
        ang = 1 / myArc.Radius
        points(0) = myArc.startPoint(0)
        points(1) = myArc.startPoint(1)
        adir = ang
        For x = 2 To UBound(points) - 2 Step 2
            mypolarpoint = ThisDrawing.Utility.PolarPoint(myArc.Center, myArc.StartAngle + adir, myArc.Radius)
            adir = adir + ang
            points(x) = mypolarpoint(0)
            points(x + 1) = mypolarpoint(1)
        Next x
        points(UBound(points) - 1) = myArc.endPoint(0)
        points(UBound(points) - 0) = myArc.endPoint(1)
        Set retObj(i) = ThisDrawing.ModelSpace.AddLightWeightPolyline(points)
        retObj(i).Update
        
       
        
        myArc.Delete
        
    Next i
    
    arc2lines = retObj

End Function
 


Sub test()
    
    Dim SelPl(0 To 1) As AcadEntity
    Dim splyObj As AcadLWPolyline
    Dim newObj As AcadLWPolyline
    
    
    Dim UsersSelection As AcadSelectionSet
    
    
    Dim DrawingSelected As AcadEntity 'delete the selection set if it already exists
    Dim intPoint12 As Variant
    Dim FilterType(0) As Integer
    Dim FilterData(0) As Variant
    Dim splyCoords() As Double
    
    Dim temp As Variant
    
    Dim index As Integer
    
    
    With ThisDrawing
        On Error Resume Next
        .SelectionSets("CurrentSelection").Delete
        'get selection from user
        MsgBox "Select objects! Hit Enter to finish!"
        Set UsersSelection = .SelectionSets.add("CurrentSelection")
        
        FilterType(0) = 0
        FilterData(0) = "LWPolyline"
        
        UsersSelection.SelectOnScreen FilterType, FilterData
        Set SelPl(0) = UsersSelection.Item(0)
        Set SelPl(1) = UsersSelection.Item(1)
        
        intPoint12 = SelPl(0).IntersectWith(SelPl(1), acExtendNone)
         
        
        splyCoords = SelPl(0).Coordinates
        splyCoords(7) = 2000
        
        SelPl(0).Update
        
        
        Set newObj = ThisDrawing.ModelSpace.AddLightWeightPolyline(splyCoords)
        newObj.Closed = True
        
        
        Debug.Print " "
        
        
    End With

End Sub

Attribute VB_Name = "MyMath"
Function getLinearEQuationA(ByVal x1 As Double, ByVal y1 As Double, ByVal x2 As Double, ByVal y2 As Double) As Double
    Dim dx As Double
    Dim ret As Double
    dx = x2 - x1
    If dx = 0 Then
        dx = 1
    End If
    
    ret = (y2 - y1) / dx
    
    getLinearEQuationA = ret

End Function

Function getLinearEQuationC(ByVal x1 As Double, ByVal y1 As Double, ByVal x2 As Double, ByVal y2 As Double) As Double

    getLinearEQuationC = -getLinearEQuationA(x1, y1, x2, y2) * x1 + y1

End Function


Function getShortestDistance(ByVal x1 As Double, ByVal y1 As Double, ByVal x2 As Double, ByVal y2 As Double, ByVal x As Double, ByVal y As Double) As Double

    Dim a, b, c, d As Double

    a = getLinearEQuationA(x1, y1, x2, y2)
    b = -1
    c = getLinearEQuationC(x1, y1, x2, y2)
    
    d = Abs((a * x + b * y + c)) / Sqr(a * a + b * b)
    
    Debug.Print ""
    getShortestDistance = d


End Function


Function getDistance(ByVal x1 As Double, ByVal y1 As Double, ByVal x2 As Double, ByVal y2 As Double) As Double

    getDistance = Sqr((x2 - x1) * (x2 - x1) + (y2 - y1) * (y2 - y1))

End Function



Function getAngleEx(ByVal cx As Double, ByVal cy As Double, ByVal x1 As Double, ByVal y1 As Double, ByVal x2 As Double, ByVal y2 As Double) As Double

    getAngleEx = ArcTan2((x2 - cx), (y2 - cy)) - ArcTan2((x1 - cx), (y1 - cy))
    
End Function


Function getAngle(ByVal x1 As Double, ByVal y1 As Double, ByVal x2 As Double, ByVal y2 As Double) As Double

    Dim dx, dy, rad As Double

    dx = x2 - x1
    dy = y2 - y1

    
    rad = ArcTan2(dx, dy)
    
    getAngle = rad
    
End Function

Function crossXY(ByVal cx As Double, ByVal cy As Double, ByVal x1 As Double, ByVal y1 As Double, ByVal x2 As Double, ByVal y2 As Double) As Double()

    Dim d, r As Double
    Dim th, rad, radex As Double
    Dim nx, ny As Double
    Dim dx, dy As Double
    Dim ret(0 To 2) As Double
    
 
    d = getShortestDistance(x1, y1, x2, y2, cx, cy)
    
    rad = getAngle(x1, y1, x2, y2)
    
    rad = Abs(rad)
    
    If rad > 0 And rad > PI_2 Then
        rad = PI - rad
    End If
    
    If rad < 0 And rad < -PI_2 Then
        rad = PI + rad
    End If
    
    
    
    radex = getAngleEx(x1, y1, cx, cy, x2, y2)
    
    radex = Abs(radex)
    
    r = getDistance(x1, y1, cx, cy)
    
    
    'r = d / Tan(radex)
    dx = r * Cos(rad)
    dy = r * Sin(rad)

    If x2 > x1 Then
        nx = x1 + dx
    Else
        nx = x1 - dx
    End If
    
    
    If y2 > y1 Then
        ny = y1 + dy
    Else
        ny = y1 - dy
    End If
    

    'addDonut2 cx, cy
    'addDonut2 x1, y1
    'addDonut2 x2, y2
    'addDonut2 nx, ny
    
    
    ret(0) = nx
    ret(1) = ny
    
    crossXY = ret
    

End Function

 

Sub testnewxy()
    
    Dim p1() As Double
    Dim ent2 As AcadObject
    Dim ent2p() As Double
    Dim sel As AcadSelectionSet
    Dim ddd() As Double
    Dim ret() As Double
    
    With ThisDrawing
        On Error Resume Next
        .SelectionSets("CurrentSelection").Delete
        Set sel = .SelectionSets.add("CurrentSelection")
        
        p1 = ThisDrawing.Utility.getPoint(, "Enter a point: ")
        ThisDrawing.Utility.getEntity ent2, ent2p, "Enter a Entity: "
        
        ddd = ent2.Coordinates
        
        ret = crossXY(p1(0), p1(1), ddd(0), ddd(1), ddd(2), ddd(3))
        
        
        ThisDrawing.ModelSpace.addLine p1, ret
        
        Debug.Print ""
        
        
    End With
    
    'NewXY 0, 2, 4, 4, 1, 5
    
    
End Sub

Sub testdistance()

    Dim d, r As Double
    Dim th, rad, radex As Double
    Dim nx, ny As Double
 
    d = getShortestDistance(0, 2, 4, 4, 1, 5)
    
    rad = getAngle(0, 2, 4, 4)
    radex = getAngleEx(0, 2, 4, 4, 1, 5)
    
    
    r = d / Tan(radex)

    nx = r * Cos(rad)
    ny = r * Sin(rad)

    Debug.Print ""
    
End Sub

Attribute VB_Name = "Test"


Sub SelectRawData()
    Dim i, ii, x, y As Integer
    Dim FilterType(0) As Integer
    Dim FilterData(0) As Variant
    Dim UsersSelection As AcadSelectionSet
    Dim selObj() As AcadEntity
    Dim ret As Integer
    Dim arcObjs() As AcadEntity
    Dim ddd() As Double
    Dim x2, y2 As Variant
    Dim count As Integer
    Dim newv(0 To 1) As Double
    
    
    With ThisDrawing
        On Error Resume Next
        .SelectionSets("CurrentSelection").Delete
        Set UsersSelection = .SelectionSets.add("CurrentSelection")
        
        
        FilterType(0) = 0
        FilterData(0) = "LWPolyline"
        
        UsersSelection.SelectOnScreen FilterType, FilterData
        
        
        count = getEntitySize(UsersSelection, "AcDbPolyline") - 1 'AcDbArc
        
        ReDim selObj(0 To count) As AcadEntity
        
        For i = 0 To count
            Set selObj(i) = UsersSelection.Item(i)
            Debug.Print " "
             
        Next i
        
        
    End With
    
    
    vx = 1194.35534891423
    vy = 2999.85414787302
    newv(0) = vx: newv(1) = vy
    
    For i = 0 To count
        ddd = selObj(i).Coordinates
        count = UBound(ddd)
        
        x1 = ddd(count - 1)
        y1 = ddd(count)
        
        For ii = 0 To count Step 2
        
            x2 = ddd(ii)
            y2 = ddd(ii + 1)
            
            f = (y2 - y1) / (x2 - x1)
            
            f1 = (vy - y1) / (vx - x1)
            f2 = (y2 - vy) / (x2 - vx)
            
            If Abs(f1 - f2) < 0.00001 Then
                addDonut x2, y2
                addDonut x1, y1
                
                selObj(i).addVertex ii / 2, newv
                selObj(i).Update
            
            End If
            
            x1 = x2
            y1 = y2
            
        Next ii
    Next i
    
    
    
    Debug.Print " "
    
    
End Sub

 



Function Step2()

 
    
    

End Function

Attribute VB_Name = "Test2"
Private Const PI As Double = 3.14159265358979
Private Const PI_2 As Double = 1.5707963267949


Sub Createcircle2()
    Dim i, ii, x, y As Integer
    Dim FilterType(0) As Integer
    Dim FilterData(0) As Variant
    Dim UsersSelection As AcadSelectionSet
    Dim selObj() As AcadEntity
    Dim ret As Integer
    Dim arcObjs() As AcadEntity
    Dim ddd() As Double
    Dim x2, y2 As Variant
    Dim count As Integer
    Dim newv(0 To 1) As Double
    Dim centerPoint(0 To 2) As Double
    
    Dim returnObj1 As AcadObject
    Dim returnObj3 As AcadObject
    
    Dim retArc As AcadArc
    
    Dim p1(0 To 2) As Double
    Dim p2() As Double
    Dim p3(0 To 2) As Double
    
    Dim retLine As AcadEntity
    Dim dout1() As Double
    Dim dout2() As Double
    Dim nnnn As Variant
    Dim newp1() As Double
    Dim newp2() As Double
    
    With ThisDrawing
        On Error Resume Next
        .SelectionSets("CurrentSelection").Delete
        Set UsersSelection = .SelectionSets.add("CurrentSelection")

        
        ThisDrawing.SetVariable "osmode", 512
        ThisDrawing.Utility.getEntity returnObj1, tmp, "Enter a point 1: "
            
        p1(0) = tmp(0)
        p1(1) = tmp(1)
            
        ThisDrawing.SetVariable "osmode", 0
        p2 = ThisDrawing.Utility.getPoint(, "Enter a point2: ")
         
        ThisDrawing.SetVariable "osmode", 512
        ThisDrawing.Utility.getEntity returnObj3, tmp, "Enter a point 3: "
        
        p3(0) = tmp(0)
        p3(1) = tmp(1)
        
        
        Set retArc = getArcBy3P(p1, p2, p3) '세점을 지나는 아크를 생성
        
        
        Set retLine = arc2line(retArc)  '아크를 라인으로 변경
        retArc.Delete
        retArc.Update
        retLine.Update
        
    
        Debug.Print ""
         
    End With
    
    
    nnnn = addCrossVertext(returnObj1, returnObj3)  '도로의 접점 추가
    
   
    newp1 = findVertex(returnObj1, retLine)   '아크와 도로(새도로)의 접점 추가
    newp2 = findVertex(returnObj3, retLine)   '아크와 도로(구도로)의 접점 추가
   
   
   
   
   Debug.Print ""
   
    'dout1 = searchOutLine(plroad(0), plObjs(0), plObjs(1))
    
    'ThisDrawing.ModelSpace.AddLightWeightPolyline(dout1).color = acRed
    
    'dout2 = searchInnerLine(plroad(1), plObjs(0), plObjs(1))
    
End Sub



Function searchInnerLine1(plobj As AcadEntity, f1obj As AcadEntity) As Double()
    searchInnerLine = searchCrossLine1(plobj, f1obj, True)
End Function

Function searchOutLine1(plobj As AcadEntity, f1obj As AcadEntity) As Double()

    searchOutLine = searchCrossLine1(plobj, f1obj, False)

End Function


Function searchCrossLine1(plobj As AcadEntity, f1obj As AcadEntity, isinner As Boolean) As Double()

    Dim dpl() As Double
    Dim df1() As Double
    Dim point As Double
    
    Dim f1idx, f1idxn As Integer    '필렛1 접점 인덱스
    
    Dim index1, index1n As Integer   '폴리라인 접점 인덱스
    
    
    Dim dret() As Double    '리턴좌표
    Dim itotal As Integer
    
    'Set ret = Nothing
    
    dpl = plobj.Coordinates '폴리라인
    df1 = f1obj.Coordinates '필렛1
    

    x = df1(0)
    y = df1(1)
    
    
    index1 = searchIndex(dpl, x, y)
    
    If index1 = -1 Then
        count = UBound(df1)
        
        x = df1(count - 1)
        y = df1(count)
        
        index1 = searchIndex(dpl, x, y)
        f1idx = count - 1
        f1idxn = count - 3
    Else
        f1idx = 0
        f1idxn = 2
        
    
    End If
    
    

    If index1 + 2 > UBound(dpl) Then
        index1n = index1 - 2
    Else
        index1n = index1 + 2
    End If


    cx = dpl(index1)
    cy = dpl(index1 + 1)
    
    x1 = dpl(index1n)
    y1 = dpl(index1n + 1)
    
    x2 = df1(f1idxn)
    y2 = df1(f1idxn + 1)

    'addDonut3 cx, cy
    'addDonut3 x1, y1
    'addDonut3 x2, y2
    


    rad = Abs(Atn((y2 - cy) / (x2 - cx)) - Atn((y1 - cy) / (c1 - cx)))
    
    
    
    If (rad < 1.571) = isinner Then '삭제영역에 해당함
    
        itotal = UBound(dpl)
        If index2 = 0 Then
            index2 = itotal
        End If
        
        If index2 > index1 Then     '올바른 방향임
            count = index2 - index1 + 2
            ReDim dret(0 To count) As Double
            
            idx = 0
            
            For i = index1 To index2 + 2 Step 2
            
                If i > itotal Then
                    dret(idx) = dpl(i - (itotal + 1))
                    idx = idx + 1
                    dret(idx) = dpl(i - (itotal + 1) + 1)
                    idx = idx + 1
                Else
                    dret(idx) = dpl(i)
                    idx = idx + 1
                    dret(idx) = dpl(i + 1)
                    idx = idx + 1
                End If
            
                'addDonut3 dret(idx - 2), dret(idx - 1)
            Next
        
        Else
            count = index1 - index2 + 1
            ReDim dret(0 To count) As Double
            
            idx = 0
            
            For i = index2 To index1 + 1 Step 2
                dret(idx) = dpl(i)
                idx = idx + 1
                dret(idx) = dpl(i + 1)
                idx = idx + 1
            Next
            'count = index1 - index2 + 1
            'ReDim dret(0 To count) As Double
            
            'idx = 0
            'For i = index1 To index2 Step -2
            '   dret(idx) = dpl(i)
            '   idx = idx + 1
            '   dret(idx) = dpl(i + 1)
            '   idx = idx + 1
            '   addDonut3 dpl(i), dpl(i + 1)
            
            'Next
        
            Debug.Print " "
            
        
        End If
        
    Else
        If index2 > index1 Then
        
            count = index1 + UBound(dpl) - index2 + 2   'y좌표 2개라서 +2
            ReDim dret(0 To count) As Double
            idx = 0
        
            For i = index2 To UBound(dpl)   '개수만큼 찾기때문에 y가 포함됨 +1 안함
                dret(idx) = dpl(i)
                idx = idx + 1
            Next
                    
            For i = 0 To index1 + 1 'y좌표 포함해야하므로 +1
                dret(idx) = dpl(i)
                idx = idx + 1
            Next
            
            
            Debug.Print
            
            
            
        Else
        
        End If
    
    End If
    
    
    
    searchCrossLine = dret
    

End Function

Function searchIndex(d() As Double, ByVal x As Double, ByVal y As Double) As Integer

    Dim index As Integer
    
    index = -1
    
    For i = 0 To UBound(d) Step 2
    
        If d(i) = x And d(i + 1) = y Then
            index = i
        End If
    
    Next


    searchIndex = index
    
End Function

Attribute VB_Name = "Test3"


Sub test4()

    Dim plroad() As AcadEntity
    Dim ret As Variant
    
    plroad = selectPolylineObs  'select two polylines(one is a source, the ohter is a target entity.
     
    
    ret = addCrossVertext(plroad(0), plroad(1))
    
    
    Set temp = ThisDrawing.ActiveLayer
    Set pp = plroad(0)
    
    Debug.Print "ActiveLayer: " & temp.Name
    pp.Layer = temp.Name
    
    
    

End Sub


Sub test77()

    Dim selec As New ClsSelEntity
    Dim ent As AcadEntity
    Dim pt As New clsPoint
    
    selec.selectPolyline ("Get Polyline 1: ")
    Set ent = selec.getEntity
    Set pt = selec.getPoint
        
    Debug.Print ""
    

End Sub


Sub test78()

    Dim seler As New ClsSelReal
    Dim rad As Double
    Dim test As Variant
    
    rad = seler.selectReal
    
    Debug.Print " "

End Sub

Sub test79()


    Dim seles As New clsSelSets
    Dim ent As AcadEntity
    
    Set ent = seles.selectArc
    

End Sub
 
Sub testSelection()

    Dim newroad As AcadEntity
    Dim basePnt1 As Variant
        
    On Error GoTo errControl
    
Start:
    ThisDrawing.Utility.getEntity newroad, basePnt1, "Get Object1: "
    
    
errControl:
    
    If Err.Description = "Method 'GetEntity' of object 'IAcadUtility' failed" Then
    
        If CheckKey(VK_ESCAPE) = True Then
            Debug.Print "End"
        
            End
        Else
            Debug.Print "Resume"
            Resume
        End If
    Else
        MsgBox Err.Description
    End If
    

End Sub

Sub test56()
    Dim plroad() As AcadEntity
    Dim ret As Variant
    Dim rad As Double
    
    Dim newroad As AcadObject
    Dim basePnt1 As Variant
    
    Dim oldroad As AcadObject
    Dim basePnt2 As Variant
    
    Dim pt1 As New clsPoint
    Dim pt2 As New clsPoint
    
    
    Dim pr1 As New clsPolygonReader
    Dim pr2 As New clsPolygonReader
    
    Dim line1 As AcadLine
    Dim line2 As AcadLine
    Dim np3 As New clsPoint
    Dim result As AcadLine
    
    Dim retArc As AcadEntity
 
    ThisDrawing.Utility.getEntity newroad, basePnt1, "Get Object1: "
    'ret = addCrossVertext(plroad(0), plroad(1))
    
    ThisDrawing.Utility.getEntity oldroad, basePnt2, "Get Object2: "
    'ret = addCrossVertext(plroad(0), plroad(1))
    
    ptIntersection = searchCrossVertext(newroad, oldroad)
    
    pt1.x = basePnt1(0)
    pt1.y = basePnt1(1)
    
    pt2.x = basePnt2(0)
    pt2.y = basePnt2(1)
    
    
    Set np3 = getNearPoint2(ptIntersection, pt2)
    
    'addDonut5 np3.x, np3.y
    
    pr1.init newroad
    Set line1 = pr1.getLine(pt1)
    
    pr2.init oldroad
    Set line2 = pr2.getLine(pt2)
    
    Set result = getShortestLine(line2, pt2, np3)
    
    
    
    'line1.Handle
    'line2.Handle
    
    'Application.ActiveDocument.SendCommand "_chamfer" & vbCr & "D" & vbCr & "1" & vbCr & "1" & vbCr & "(HandEnt """ & line1.Handle & """)" & vbCr & "(HandEnt """ & line2.Handle & """)" & vbCr
    Application.ActiveDocument.SendCommand "_fillet" & vbCr & "T" & vbCr & "N" & vbCr & "r" & vbCr & "3" & vbCr & "(HandEnt """ & line1.Handle & """)" & vbCr & "(HandEnt """ & result.Handle & """)" & vbCr
    
    
    If line2.Handle <> result.Handle Then
        result.Delete
    End If
    
    line1.Delete
    line2.Delete
    
    Dim ssetObj As AcadSelectionSet
    Set ssetObj = ThisDrawing.ActiveSelectionSet
    
    
    
    ssetObj.Select acSelectionSetLast
    
     For Each ent In ssetObj
        Set retArc = ent
     Next
    
    
    
    
    
    
    Debug.Print " "


End Sub


Function getShortestLine(line As AcadLine, ct As clsPoint, pt As clsPoint) As AcadLine

    Dim newline As AcadLine
    
    Dim sp() As Double
    Dim ep() As Double
        
    L12 = line.Length
    
    sp = line.startPoint
    ep = line.endPoint
    
    L13 = getDistance(sp(0), sp(1), pt.x, pt.y)
    L23 = getDistance(ep(0), ep(1), pt.x, pt.y)
    
    L1C = getDistance(sp(0), sp(1), ct.x, ct.y)
    L2C = getDistance(ep(0), ep(1), ct.x, ct.y)
    
    
    If L12 > L13 And L12 > L23 Then
        
        If L1C < L13 Then
            'L13
            sp(0) = sp(0)
            sp(1) = sp(1)
            ep(0) = pt.x
            ep(1) = pt.y
            
        Else        ' L1C < L23
            'L23
            sp(0) = ep(0)
            sp(1) = ep(1)
            ep(0) = pt.x
            ep(1) = pt.y
            
        End If
        
        Set newline = ThisDrawing.ModelSpace.addLine(sp, ep)
        
        'line.Delete
    ElseIf L12 > L23 And L12 > L13 Then
        
       'L13
        sp(0) = sp(0)
        sp(1) = sp(1)
        ep(0) = pt.x
        ep(1) = pt.y
        
        Set newline = ThisDrawing.ModelSpace.addLine(sp, ep)
        'line.Delete
   
    Else
    
        Set newline = line
    
    End If
    
    
    Debug.Print ""
    
    Set getShortestLine = newline


End Function


Sub test55()

    Dim plroad() As AcadEntity
    Dim ret As Variant
    Dim rad As Double
    
    plroad = selectObjs 'select two polylines(one is a source, the ohter is a target entity.
     
    
    'ret = addCrossVertext(plroad(0), plroad(1))
    
    
    
    
    
    
    Set tmp1 = plroad(0)
    Set tmp2 = plroad(1)
    
    
    tmp3 = tmp1.Handle
    tmp4 = tmp2.Handle
    
    Application.ActiveDocument.SendCommand "_chamfer" & vbCr & "D" & vbCr & "1" & vbCr & "1" & vbCr & "(HandEnt """ & tmp1.Handle & """)" & vbCr & "(HandEnt """ & tmp2.Handle & """)" & vbCr
    'Application.ActiveDocument.SendCommand "_fillet" & vbCr & "T" & vbCr & "N" & vbCr & "r" & vbCr & "3" & vbCr & "(HandEnt """ & tmp1.Handle & """)" & vbCr & "(HandEnt """ & tmp2.Handle & """)" & vbCr
    
    
    
    
    Debug.Print " "
    

End Sub


Sub LineFillet()



ThisDrawing.SendCommand "_fillet" & vbCr & "T" & vbCr & "N" & vbCr & "r" & vbCr & "3" & vbCr
ThisDrawing.SendCommand "(HandEnt """ & r.Handle & """)" & vbCr
ThisDrawing.SendCommand "(HandEnt """ & plineObj.Handle & """)" & vbCr


Debug.Print "done"
   'ThisDrawing.SendCommand "fillet T N r 3"
   'ThisDrawing.ModelSpace.ad
           
End Sub

 
Public Sub testFillet()

    Dim doc As Document

    doc = Application.DocumentManager.MdiActiveDocument

    Dim ed As Editor
    ed = doc.Editor

    Dim Db As Database
    Db = doc.Database



    Dim pEntRes1 As PromptEntityResult
    pEntRes1 = ed.getEntity("Select first line to Fillet")

    If pEntRes1.Status <> PromptStatus.OK Then

        Return

    End If



    Dim obj1 As String
    obj1 = pEntRes1.ObjectID.ObjectClass.Name



    Dim pEntRes2 As PromptEntityResult
    pEntRes2 = ed.getEntity("Select second line to Fillet")

    If pEntRes2.Status <> PromptStatus.OK Then

        Return

    End If



    obj1 = pEntRes2.ObjectID.ObjectClass.Name


    Dim strHandle1 As String
    
    strHandle1 = pEntRes1.ObjectID.Handle.ToString()

    Dim strEntName1 As String
    strEntName1 = "(handent """ & strHandle1 & """)"



    Dim strHandle2 As String
    strHandle2 = pEntRes2.ObjectID.Handle.ToString()

    Dim strEntName2 As String
    strEntName2 = "(handent """ & strHandle2 & """)"

    Dim strCommand As String
    strCommand = "_fillet" + vbCr + "r" + vbCr + "0.495" + vbCr + strEntName1 + vbCr + strEntName2 + vbCr

    doc.AcadDocument.SendCommand (strCommand)



End Sub

Public Sub prob2()
    Dim ssetObj As AcadSelectionSet
    Set ssetObj = ThisDrawing.PickfirstSelectionSet
    ssetObj.Clear
    
    ' asks for an entity and put it into the sset
    Dim returnObj As AcadObject
    Dim basePnt As Variant
    ThisDrawing.Utility.getEntity returnObj, basePnt, "Select object: "
    Dim objlist(0) As AcadObject
    Set objlist(0) = returnObj
    ' difference from previous version
    Dim objlistvar As Variant
    objlistvar = objlist
    ssetObj.AddItems objlistvar
    ' then delete the sset to make it the "previous selection set"
    ssetObj.Delete
    
    Set ssetObj = ThisDrawing.PickfirstSelectionSet ' or whatever ss
    ssetObj.Select acSelectionSetPrevious
End Sub



Public Sub FilletVertex(ByVal LWPline As AcadLWPolyline, _
    ByVal VertexNumber As Integer, ByVal Radius As Double, _
    Optional AsChamfer As Boolean)

    On Error Resume Next: DoEvents
    
    Dim IsConcave As Boolean
    Dim AngleToVertex As Double
    Dim AngleFromVertex As Double
    Dim AngleIncluded As Double
    Dim ptList As Variant
    Dim LastVertex As Integer
    Dim PrevVertex As Integer
    Dim NextVertex As Integer
    Dim Bulge As Double
    Dim pt1 As Variant
    Dim pt2 As Variant
    Dim pt2a As Variant
    Dim pt2b As Variant
    Dim pt3 As Variant
    Dim VertexA(1) As Double
    Dim VertexB(1) As Double
    Dim chamfer As Double
    Dim Util As AcadUtility
    
    Set Util = ThisDrawing.Utility

    If Radius = 0 Then
        Exit Sub
    ElseIf Radius < 0 Then
        Radius = Abs(Radius)
        IsConcave = True
    End If
    
    With LWPline
        ptList = .Coordinates
        
        LastVertex = (UBound(ptList) - 1) / 2
        If VertexNumber > LastVertex Then VertexNumber = 0
        NextVertex = VertexNumber + 1
        PrevVertex = VertexNumber - 1
        If NextVertex > LastVertex Then NextVertex = 0
        If PrevVertex < 0 Then PrevVertex = LastVertex
        
        If NextVertex = PrevVertex Then Exit Sub
        
        pt1 = .Coordinate(PrevVertex)
        pt2 = .Coordinate(VertexNumber)
        pt3 = .Coordinate(NextVertex)
    
        ReDim Preserve pt1(2): pt1(2) = 0
        ReDim Preserve pt2(2): pt2(2) = 0
        ReDim Preserve pt3(2): pt3(2) = 0
        
        AngleToVertex = Util.AngleFromXAxis(pt2, pt1)
        AngleFromVertex = Util.AngleFromXAxis(pt2, pt3)
        
        AngleIncluded = (AngleToVertex - AngleFromVertex)
        If AngleIncluded > PI Then
            AngleIncluded = AngleIncluded - (2 * PI)
        ElseIf AngleIncluded < -PI Then
            AngleIncluded = AngleIncluded + (2 * PI)
        End If
        

            
        If IsConcave Then
            chamfer = Radius
        Else
            chamfer = Radius * _
                Tan((PI - (Abs(AngleIncluded))) / 2)
        End If
        
        pt2b = Util.PolarPoint(pt2, _
            AngleFromVertex, chamfer)
        VertexB(0) = pt2b(0): VertexB(1) = pt2b(1)
        .Coordinate(VertexNumber) = VertexB
        
        pt2a = Util.PolarPoint(pt2, _
            AngleToVertex, chamfer)
        VertexA(0) = pt2a(0): VertexA(1) = pt2a(1)
        .addVertex VertexNumber, VertexA
        
        If Not AsChamfer Then

            If IsConcave Then
                Bulge = Tan((AngleIncluded) / -4#)
            Else
                Bulge = Tan((IIf(AngleIncluded > 0, PI, -PI) - AngleIncluded) / 4#)
            End If
            
             .SetBulge VertexNumber, Bulge

         End If
    End With
End Sub


Sub simplifyObject()    ' 오류

    Dim Userselection As AcadSelectionSet

    ThisDrawing.SelectionSets("CurrentSelection").Delete
    Set UsersSelection = ThisDrawing.SelectionSets.add("CurrentSelection")
        
    UsersSelection.SelectOnScreen
         
    
    
    tmp3 = UsersSelection.Handle

    ThisDrawing.SendCommand "(setq clean_id (tpm_cleanalloc))"
    ThisDrawing.SendCommand "(setq clean_var_id (tpm_varalloc))"
    ThisDrawing.SendCommand "(setq action_var_id (tpm_varalloc))"
    
    ThisDrawing.SendCommand "(tpm_varset clean_var_id ""CLEAN_TOL"" 2)"
    ThisDrawing.SendCommand "(tpm_varset clean_var_id ""INCLUDEOBJS_AUTOSELECT"" 0)"
    
    ThisDrawing.SendCommand "(tpm_cleanactionlistins clean_var_id 0 128 clean_var_id)"
    ThisDrawing.SendCommand "(setq DrwCleanresult (tpm_cleaninit clean_id clean_var_id (HandEnt """ & tmp1.Handle & """)))"
    ThisDrawing.SendCommand "(setq DrwCleanresult (tpm_cleanstart clean_id))"
    ThisDrawing.SendCommand "(tpm_cleanend clean_id)"
    
   

End Sub

Attribute VB_Name = "chamferModule"


Function findVertexAtLine(ent As AcadEntity, ent2 As AcadLine) As Double()

    Dim ddd(0 To 3) As Double
    Dim filletpoint(0 To 7) As Double   '8
        
    
    
    ddd(0) = ent2.startPoint(0)
    ddd(1) = ent2.startPoint(1)
    ddd(2) = ent2.endPoint(0)
    ddd(3) = ent2.endPoint(1)
            
    count = UBound(ddd)
    
    vx = ddd(count - 1)
    vy = ddd(count)
    
    newp = addVertex(ent, vx, vy)
    
    If newp(0) <> 0 And newp(1) <> 0 Then
    
        filletpoint(index) = newp(0)
        index = index + 1
        filletpoint(index) = newp(1)
        index = index + 1
         
    Else
        vx = ddd(0)
        vy = ddd(1)
        
        newp = addVertex(ent, vx, vy)
        
        If newp(0) <> 0 And newp(1) <> 0 Then
        
            filletpoint(index) = newp(0)
            index = index + 1
            filletpoint(index) = newp(1)
            index = index + 1
        End If
    End If
    
    findVertexAtLine = newp

End Function

Attribute VB_Name = "clsChamfer2"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private oldroad As AcadEntity
Private newroad As AcadEntity
Private fillet As AcadEntity

Private ptIntersection As Variant


Public Function load()

    Dim pt1 As New clsPoint
    Dim retLine As AcadLine
    Dim tmp As Variant
    
    
    Dim np1 As New clsPoint
    Dim np2 As New clsPoint
    Dim np3 As New clsPoint
    
    Dim splitter As New clsSplitter
    Dim pr As New clsPolygonReader
    
    Dim newroadsplit() As Double
    Dim oldroadsplit() As Double
    Dim additionsplit(0 To 3) As Double
    
    Dim merge As New ClsMerger
    Dim resultd() As Double
    Dim result As AcadEntity
    Dim test As Boolean
    
    
    Dim pt3 As New clsPoint
    
    
    Dim line1 As AcadLine
    Dim line2 As AcadLine
    
    Dim pr1 As New clsPolygonReader
    Dim pr2 As New clsPolygonReader
    
    
    Dim selec1 As New ClsSelEntity
    Dim selec2 As New ClsSelEntity
    
    
    Dim seler As New ClsSelReal
    Dim frad As Double
    
    Dim selecs As New clsSelSets
    
    selec1.selectPolyline ("Get Polyline 1: ")
    Set newroad = selec1.getEntity
    Set pt1 = selec1.getPoint
    
    selec2.selectPolyline ("Get Polyline 2: ")
    Set oldroad = selec2.getEntity
    Set pt3 = selec2.getPoint
    
    
    ptIntersection = searchCrossVertext(newroad, oldroad)
    
    
    Set np3 = getNearPoint2(ptIntersection, pt3)
    
    'addDonut5 pt1.x, pt1.y
    'addDonut5 pt3.x, pt3.y
    'addDonut5 np3.x, np3.y
    
    
    pr1.init newroad
    Set line1 = pr1.getLine(pt1)
    
     
    pr2.init oldroad
    Set line2 = pr2.getLine(pt3)
    
     
    
    Set resultpl = getShortestLine(line2, pt3, np3)
    
    
    frad = seler.selectReal
    
    
    Application.ActiveDocument.SendCommand "_chamfer" & vbCr & "D" & vbCr & frad & vbCr & frad & vbCr & "(HandEnt """ & line1.Handle & """)" & vbCr & "(HandEnt """ & line2.Handle & """)" & vbCr
    'Application.ActiveDocument.SendCommand "_fillet" & vbCr & "T" & vbCr & "N" & vbCr & "r" & vbCr & frad & vbCr & "(HandEnt """ & line1.Handle & """)" & vbCr & "(HandEnt """ & resultpl.Handle & """)" & vbCr
    
    Set retLine = selecs.selectLine
    
    'Set retArc = selectArcObj
    
    'Set ssetObj = ThisDrawing.ActiveSelectionSet
    '
    'ssetObj.Select acSelectionSetLast
    '
    'For Each ent In ssetObj
    '   Set retArc = ent
    'Next
    
    If line2.Handle <> resultpl.Handle Then
        resultpl.Delete
    End If
    
    line1.Delete
    line2.Delete
    
    
    
    Debug.Print "chamfer created"
    
    
    ptIntersection = searchCrossVertext(newroad, oldroad)
    
    
    For i = 0 To UBound(ptIntersection) Step 3
        addDonutY ptIntersection(i), ptIntersection(i + 1)
        
    Next i
    
    
    newp1 = findVertexAtLine(newroad, retLine)   '아크와 도로(새도로)의 접점 추가
    newp2 = findVertexAtLine(oldroad, retLine)   '아크와 도로(구도로)의 접점 추가
   
   
    np1.initXy newp1(0), newp1(1)
    np2.initXy newp2(0), newp2(1)
    
    
    Debug.Print "np1: " & np1.x & ", " & np1.y
    Debug.Print "np2: " & np2.x & ", " & np2.y
   
   
    additionsplit(0) = np1.x
    additionsplit(1) = np1.y
    additionsplit(2) = np2.x
    additionsplit(3) = np2.y
    
   
    Set np3 = getFarPoint2(ptIntersection, np2)     '기존도로 아크 접점에서 먼 지점을 찾는다
    
    
    addVertex oldroad, np3.x, np3.y     '기존도로에 접점추가
    

   
    Debug.Print "cross point created"
    
    pr.init newroad
    pr.setIndexByPoint np1
    pr.checkDirection pt3
    
    'addDonut5 np3.x, np3.y
    'addDonut5 np1.x, np1.y
    Debug.Print "newroad direction processed"
    
    newroadsplit = pr.splitInnerLine(np3, np1)
    'addLine newroadsplit
    
    Debug.Print "newroad split created"
   
    pr.init oldroad
    pr.setIndexByPoint np2
    pr.checkDirection pt1
    
    Debug.Print "oldroad direction processed"
    
    oldroadsplit = pr.splitInnerLine(np2, np3)
    'addLine oldroadsplit
    
    
   
    Debug.Print "oldroad split created"
        
    size1 = UBound(newroadsplit)
    size2 = UBound(additionsplit)
    size3 = UBound(oldroadsplit)
    
    merge.setSize size1 + size2 + size3 + 2
    
    
    merge.add newroadsplit
    merge.add additionsplit
    merge.add oldroadsplit
    
    
    addLine merge.getMerged
    newroad.Delete
    retLine.Delete
    
    'ThisDrawing.SendCommand "sob" & vbCr
    
End Function

Attribute VB_Name = "clsFillet"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private oldroad As AcadEntity
Private newroad As AcadEntity
Private fillet As AcadEntity

Private ptIntersection As Variant


Public Function load()

    Dim p1 As New clsPoint
    Dim p2() As Double
    Dim p3 As New clsPoint
    Dim retArc As AcadEntity
    Dim tmp As Variant
    
    
    Dim np1 As New clsPoint
    Dim np2 As New clsPoint
    Dim np3 As New clsPoint
    
    Dim splitter As New clsSplitter
    Dim pr As New clsPolygonReader
    
    Dim newroadsplit() As Double
    Dim oldroadsplit() As Double
    Dim filletsplit() As Double
    
    Dim merge As New ClsMerger
    Dim resultd() As Double
    Dim result As AcadEntity
    Dim test As Boolean
    
    
    ThisDrawing.SetVariable "osmode", 512
    ThisDrawing.Utility.getEntity newroad, tmp, "Enter a point 1: "
        
    p1.initPt tmp
    
    
    
        
    ThisDrawing.SetVariable "osmode", 0
    p2 = ThisDrawing.Utility.getPoint(, "Enter a point2: ")
     
    ThisDrawing.SetVariable "osmode", 512
    ThisDrawing.Utility.getEntity oldroad, tmp, "Enter a point 3: "
    
    p3.initPt tmp
    
    
    Debug.Print "p1: " & p1.x & ", " & p1.y
    Debug.Print "p2: " & p2(0) & ", " & p2(1)
    Debug.Print "p3: " & p3.x & ", " & p3.y
    
    test = False
    
    If test = True Then
        p1.x = 2775.17827046719
        p1.y = 2603.02116973727
        p2(0) = 2773.78983919124
        p2(1) = 2605.02952223306
        p3.x = 2770.42837317067
        p3.y = 2606.45362901053
    End If
    
    
    Set retArc = getArcBy3P(p1.getPoints(), p2, p3.getPoints()) '세점을 지나는 아크를 생성
    Set fillet = arc2line(retArc)  '아크를 라인으로 변경
    filletsplit = fillet.Coordinates
    
    retArc.Delete
    
    
    Debug.Print "fillet created"
    
    
    ptIntersection = searchCrossVertext(newroad, oldroad)
    
    newp1 = findVertex(newroad, fillet)   '아크와 도로(새도로)의 접점 추가
    newp2 = findVertex(oldroad, fillet)   '아크와 도로(구도로)의 접점 추가
   
   
    np1.initXy newp1(0), newp1(1)
    np2.initXy newp2(0), newp2(1)
    
    
    Debug.Print "np1: " & np1.x & ", " & np1.y
    Debug.Print "np2: " & np2.x & ", " & np2.y
    
   
    Set np3 = getFarPoint2(ptIntersection, np2)     '기존도로 아크 접점에서 먼 지점을 찾는다
    
    
    addVertex oldroad, np3.x, np3.y     '기존도로에 접점추가
    

   
    Debug.Print "cross point created"
    
    pr.init newroad
    pr.setIndexByPoint np1
    pr.checkDirection p3
    
    'addDonut5 np3.x, np3.y
    'addDonut5 np1.x, np1.y
    Debug.Print "newroad direction processed"
    
    newroadsplit = pr.splitInnerLine(np3, np1)
    'addLine newroadsplit
    
    Debug.Print "newroad split created"
   
    pr.init oldroad
    pr.setIndexByPoint np2
    pr.checkDirection p1
    
    Debug.Print "oldroad direction processed"
    
    oldroadsplit = pr.splitInnerLine(np2, np3)
    'addLine oldroadsplit
    
    
    
    Debug.Print "oldroad split created"
        
    size1 = UBound(newroadsplit)
    size2 = UBound(filletsplit)
    size3 = UBound(oldroadsplit)
    
    merge.setSize size1 + size2 + size3 + 2
    
    
    merge.add newroadsplit
    merge.add filletsplit
    merge.add oldroadsplit
    
    
    Set result = addLine(merge.getMerged)
    newroad.Delete
    fillet.Delete
    
    ThisDrawing.SendCommand "sob" & vbCr
    
    
    Set temp = ThisDrawing.ActiveLayer
    
    result.Layer = ThisDrawing.ActiveLayer.Name
    
    
    
End Function


Private Function getArcBy3P(p1() As Double, p2() As Double, p3() As Double) As AcadArc
    Dim centerPoint(0 To 2) As Double
    Dim retOjb As AcadArc
    
    x1 = p1(0)
    y1 = p1(1)
    
    x2 = p2(0)
    y2 = p2(1)
     
    x3 = p3(0)
    y3 = p3(1)
    
    d1 = (x2 - x1) / (y2 - y1)
    d2 = (x3 - x2) / (y3 - y2)
    
    cx = ((y3 - y1) + (x2 + x3) * d2 - (x1 + x2) * d1) / (2 * (d2 - d1))
    cy = -d1 * (cx - (x1 + x2) / 2) + (y1 + y2) / 2
     
    r = VBA.Sqr((x1 - cx) ^ 2 + (y1 - cy) ^ 2)
    
    centerPoint(0) = cx
    centerPoint(1) = cy
    
    StartAngle = ArcTan2((x1 - cx), (y1 - cy))
    EndAngle = ArcTan2((x3 - cx), (y3 - cy))
    
    If StartAngle >= 0 And EndAngle >= 0 Then
        If StartAngle > EndAngle Then
            tmp = StartAngle
            StartAngle = EndAngle
            EndAngle = tmp
        End If
    ElseIf StartAngle < 0 And EndAngle < 0 Then
        If StartAngle > EndAngle Then
            tmp = StartAngle
            StartAngle = EndAngle
            EndAngle = tmp
        End If
    ElseIf StartAngle > 0 And EndAngle < 0 Then
        If (PI - StartAngle) + (PI + EndAngle) > PI Then
            tmp = StartAngle
            StartAngle = EndAngle
            EndAngle = tmp
        End If
    ElseIf StartAngle < 0 And EndAngle > 0 Then
        If Abs(StartAngle) + EndAngle > PI Then
            tmp = StartAngle
            StartAngle = EndAngle
            EndAngle = tmp
        End If
            
    End If
    
    
    Set retOjb = ThisDrawing.ModelSpace.AddArc(centerPoint, r, StartAngle, EndAngle)
     
    
    Set getArcBy3P = retOjb

End Function

Attribute VB_Name = "clsPoint"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Public x As Double
Public y As Double

Public Function initXy(ByVal xx As Double, ByVal yy As Double)
    x = xx
    y = yy
End Function

Public Function initPt(pt As Variant)
    x = pt(0)
    y = pt(1)
End Function


Public Function distance(pt As clsPoint) As Double
 
    Dim ret As Double
    
 
    ret = Sqr((pt.x - x) * (pt.x - x) + (pt.y - y) * (pt.y - y))

    distance = ret

End Function

Public Function getPoints() As Double()

    Dim pt(0 To 1) As Double
    
    
    pt(0) = x
    pt(1) = y
    
    getPoints = pt
    

End Function

Public Function isEquals(p As clsPoint) As Boolean


    If Int(x * P2P_TOL) = Int(p.x * P2P_TOL) And Int(y * P2P_TOL) = Int(p.y * P2P_TOL) Then
        isEquals = True
        
    Else
        isEquals = False
    End If


End Function

Attribute VB_Name = "clsPolygonReader"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private ent As AcadEntity
Private index As Integer    '현재위치
Private coord() As Double
Private size As Integer '포인트 크기(/3 - x,y,z)
Private sidx As Integer '시작지점
Private reverse As Boolean
Const C_ST = 2

Public Function init(e As AcadEntity)
    Set ent = e
    
    coord = ent.Coordinates
    size = UBound(coord)
    
    reverse = False
End Function

Public Function setIndex(i As Integer)

    index = i

End Function


Public Function setIndexByPoint(p As clsPoint)
    
    sidx = getIndexByPoint(p)
    

End Function


Public Function getIndexByPoint(p As clsPoint) As Integer

    sidx = -1


    Debug.Print "BSE: " & p.x & p.y & "==========="
    

    For i = 0 To size Step C_ST
    
        x = coord(i)
        y = coord(i + 1)
        
        'Debug.Print "idx: " & i & " > "  & x & y & "===="
        
        If Int(p.x * P2P_TOL) = Int(x * P2P_TOL) And Int(p.y * P2P_TOL) = Int(y * P2P_TOL) Then
            sidx = i
            getIndexByPoint = sidx
            Debug.Print "idx: " & i & " > " & x & y & "===="
            Exit Function
        End If
    
    Next i
    
    
    Debug.Print "result: getIndexByPoint: " & sidx
    
    If sidx = -1 Then
            Debug.Print "getIndexByPoint: " & sidx
    End If
    

End Function





Public Function checkDirection(p As clsPoint)

    Dim cp As New clsPoint
    Dim np As New clsPoint
    Dim angle As Double
    
    reverse = False
    setIndex sidx
    Set cp = getPoint(sidx)
    Set np = nextPoint
    
    'addDonut5 cp.x, cp.y
    'addDonut5 np.x, np.y
    'addDonut5 p.x, p.y
    

    'd1 = getDistance(cp.x, cp.y, p.x, p.y)
    'd2 = getDistance(np.x, np.y, p.x, p.y)

    'If d1 < d2 Then
    '    reverse = True
    'End If
    angle = getAngleEx(cp.x, cp.y, np.x, np.y, p.x, p.y)
    
    
    Debug.Print "angle: " & angle
    
    If angle < 0 And Abs(angle) > PI Then
        angle = 2 * PI + angle
    End If
    
    'addDonut5 np.x, np.y
    
    If Abs(angle) > PI_2 Then
        reverse = True
    End If
    
    Debug.Print "angle: " & angle & ", reverse: " & reverse
    
    



End Function

Private Function nextPoint() As clsPoint
    Dim p As New clsPoint
    
    
    If reverse = False Then
        index = index + C_ST
    
        If index > size Then
            index = 0
        End If
    Else
        index = index - C_ST
    
        If index < 0 Then
        index = size - C_ST + 1
        End If
    
    End If
    
    
    p.x = coord(index)
    p.y = coord(index + 1)
    
    
    Set nextPoint = p
End Function

Private Function prevPoint() As clsPoint
    Dim p As New clsPoint
    
    If reverse = False Then
        index = index - C_ST
        
        If index < 0 Then
            index = size - C_ST + 1
        End If
    Else
        index = index + C_ST
    
        If index > size Then
            index = 0
        End If
    End If
    
    
    p.x = coord(index)
    p.y = coord(index + 1)
    
    Set prevPoint = p
End Function


Public Function getPoint(idx As Integer) As clsPoint
    Dim p As New clsPoint
    
    p.x = coord(idx)
    p.y = coord(idx + 1)
    
    Set getPoint = p
End Function



Public Function splitInnerLine(startp As clsPoint, endp As clsPoint) As Double()

    Dim p As New clsPoint
    Dim np As New clsPoint
    Dim count As Integer
    Dim ret() As Double
    Dim idx As Integer

    setIndexByPoint startp
    setIndex (sidx)
    
    Set p = getPoint(sidx)
    Set np = nextPoint()
    
    count = 1
    
    Do While (np.isEquals(endp) = False And size > count)
        count = count + 1
        Set np = nextPoint()
        
    Loop
    
    
    idx = 0
    ReDim ret(0 To count * 2 + 1) As Double
    
    setIndexByPoint startp
    setIndex (sidx)
    
    Set p = getPoint(sidx)
    
    ret(idx) = p.x
    idx = idx + 1
    ret(idx) = p.y
    idx = idx + 1
    
    'addDonut5 p.x, p.y
    
    Set np = nextPoint()
    
    ret(idx) = np.x
    idx = idx + 1
    ret(idx) = np.y
    idx = idx + 1
    
    'addDonut5 p.x, p.y
    
    count = 1
    
    Do While (np.isEquals(endp) = False And size > count)
        count = count + 1
        Set np = nextPoint()
        ret(idx) = np.x
        idx = idx + 1
        ret(idx) = np.y
        idx = idx + 1
    Loop
    
    splitInnerLine = ret
    
End Function


Public Function splitOutLine(startp As clsPoint, endp As clsPoint) As Double()

    Dim p As New clsPoint
    Dim np As New clsPoint
    Dim count As Integer
    Dim ret() As Double
    Dim idx As Integer

    setIndexByPoint startp
    setIndex (sidx)
    
    Set p = getPoint(sidx)
    Set np = nextPoint()
    
    count = 1
    
    Do While (np.isEquals(endp) = False And size > count)
        count = count + 1
        Set np = nextPoint()
        
    Loop
    
    
    idx = 0
    ReDim ret(0 To count * 2 + 1) As Double
    
    setIndexByPoint startp
    setIndex (sidx)
    
    Set p = getPoint(sidx)
    
    ret(idx) = p.x
    idx = idx + 1
    ret(idx) = p.y
    idx = idx + 1
    
    Set np = nextPoint()
    
    ret(idx) = np.x
    idx = idx + 1
    ret(idx) = np.y
    idx = idx + 1
    
    count = 1
    
    Do While (np.isEquals(endp) = False And size > count)
        count = count + 1
        Set np = nextPoint()
        ret(idx) = np.x
        idx = idx + 1
        ret(idx) = np.y
        idx = idx + 1
    Loop
    
    splitInnerLine = ret
    
End Function



Public Function getLine(pt As clsPoint) As AcadLine

    Dim newp As AcadLine


    
    idx = getIndexByPoint(pt)
    setIndex (idx)
    
    
    Set newp = getLineByEntity(ent, pt.x, pt.y)
    
    
    Debug.Print ":"
    
    Set getLine = newp
    

End Function

Attribute VB_Name = "clsSelSets"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Const VK_ESCAPE = &H1B, VK_ENTER = &HD, VK_LBUTTON = &H1


Public Function selectArc()
    Dim UsersSelection As AcadSelectionSet
    Dim FilterType(0) As Integer
    Dim FilterData(0) As Variant
    Dim arcObjs As AcadEntity
    Dim count As Integer
    Dim sss As Variant
    
 
    On Error GoTo errControl
    
Start:
 
     With ThisDrawing
        On Error Resume Next
        .SelectionSets("CurrentSelection").Delete
        Set UsersSelection = .SelectionSets.add("CurrentSelection")
        
        FilterType(0) = 0
        FilterData(0) = "Arc"
        
        UsersSelection.SelectOnScreen FilterType, FilterData
        
        
        count = getEntitySize(UsersSelection, "AcDbArc")
            
        If count = 0 Then
            Resume
        End If
        
        For i = 0 To count
            Set arcObjs = UsersSelection.Item(i)
            Exit For
        Next i
    End With
    
    
errControl:
    
    Debug.Print Err.Description
    
    If Err.Description = "Invalid argument index in Item" Then
    
        If CheckKey(VK_ESCAPE) = True Or CheckKey(VK_ENTER) Then
            Debug.Print "End"
        
            End
        Else
            Debug.Print "Resume"
            Resume
        End If
    ElseIf Err.Description = "Key not found" Then
    
    
    End If
    
    
    
    
    
    Set selectArc = arcObjs
End Function


Public Function selectLine()
    Dim UsersSelection As AcadSelectionSet
    Dim FilterType(0) As Integer
    Dim FilterData(0) As Variant
    Dim arcObjs As AcadEntity
    Dim count As Integer
    Dim sss As Variant
    
 
    On Error GoTo errControl
    
Start:
 
     With ThisDrawing
        On Error Resume Next
        .SelectionSets("CurrentSelection").Delete
        Set UsersSelection = .SelectionSets.add("CurrentSelection")
        
        FilterType(0) = 0
        FilterData(0) = "Line"
        
        UsersSelection.SelectOnScreen FilterType, FilterData
        
        
        count = getEntitySize(UsersSelection, "AcLine")
            
        If count = 0 Then
            Resume
        End If
        
        For i = 0 To count
            Set arcObjs = UsersSelection.Item(i)
            Exit For
        Next i
    End With
    
    
errControl:
    
    Debug.Print Err.Description
    
    If Err.Description = "Invalid argument index in Item" Then
    
        If CheckKey(VK_ESCAPE) = True Or CheckKey(VK_ENTER) Then
            Debug.Print "End"
        
            End
        Else
            Debug.Print "Resume"
            Resume
        End If
    ElseIf Err.Description = "Key not found" Then
    
    
    End If
    
    
    
    
    
    Set selectLine = arcObjs
End Function

Attribute VB_Name = "clsSelector"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private ent As AcadEntity
Private size As Integer


Public Function init(e As AcadEntity)
    Set ent = e
    
    coord = ent.Coordinates
    size = UBound(coord)
    
End Function

Attribute VB_Name = "clsSplitter"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private src As AcadEntity
Private pt1 As clsPoint
Private pt2 As clsPoint
Private ptRef As clsPoint


Function split(ent As AcadEntity, p1 As clsPoint, p2 As clsPoint, pref As clsPoint)





End Function

Attribute VB_Name = "filletModule"
Public Const PI As Double = 3.14159265358979
Public Const PI_2 As Double = 1.5707963267949






Function arc2line(myArc As AcadArc) As AcadEntity

    Dim retObj As AcadEntity
    Dim delta As Double
    
    delta = myArc.EndAngle - myArc.StartAngle
    If delta < 0 Then delta = delta + (2 * PI)
    Dim numOfSegments As Integer
    Dim points() As Double
    'adjust below for reality
    numOfSegments = CInt(myArc.ArcLength * 10) ' length of segment = 1, last segment = remainder
    ReDim points(0 To 2 * numOfSegments + 1)
    ang = 1 / (myArc.Radius * 10)
    points(0) = myArc.startPoint(0)
    points(1) = myArc.startPoint(1)
    adir = ang
    For x = 2 To UBound(points) - 2 Step 2
        mypolarpoint = ThisDrawing.Utility.PolarPoint(myArc.Center, myArc.StartAngle + adir, myArc.Radius)
        adir = adir + ang
        points(x) = mypolarpoint(0)
        points(x + 1) = mypolarpoint(1)
    Next x
    points(UBound(points) - 1) = myArc.endPoint(0)
    points(UBound(points) - 0) = myArc.endPoint(1)
    Set retObj = ThisDrawing.ModelSpace.AddLightWeightPolyline(points)
    
    Set arc2line = retObj

End Function


Function addCrossVertext(src As AcadEntity, dst As AcadEntity) As Variant

    Dim ret As Variant
    Dim size As Integer
    
    ret = src.IntersectWith(dst, acExtendOtherEntity)   'find vertex
    size = 0
    
    
    size = UBound(ret)
    
    If size > 0 Then
        For i = 0 To size Step 3
            addDonut2 ret(i), ret(i + 1)
            
            addVertex dst, ret(i), ret(i + 1)     ' add vertext
        Next
    Else
    
    End If
    
    addCrossVertext = ret

End Function


Function findVertex(ent As AcadEntity, ent2 As AcadEntity) As Double()

    Dim ddd() As Double
    Dim filletpoint(0 To 7) As Double   '8
        
    ddd = ent2.Coordinates
    
    count = UBound(ddd)
    
    vx = ddd(count - 1)
    vy = ddd(count)
    
    newp = addVertex(ent, vx, vy)
    
    If newp(0) <> 0 And newp(1) <> 0 Then
    
        filletpoint(index) = newp(0)
        index = index + 1
        filletpoint(index) = newp(1)
        index = index + 1
         
    Else
        vx = ddd(0)
        vy = ddd(1)
        
        newp = addVertex(ent, vx, vy)
        
        If newp(0) <> 0 And newp(1) <> 0 Then
        
            filletpoint(index) = newp(0)
            index = index + 1
            filletpoint(index) = newp(1)
            index = index + 1
        End If
    End If
    
    findVertex = newp

End Function





Function addVertex(ent As AcadEntity, ByVal vx As Double, ByVal vy As Double) As Double()

    Dim newv(0 To 1) As Double
    Dim ddd() As Double
    Dim count As Integer
    Dim distance As Double

    Dim ret As Boolean
    Dim newp() As Double
    
    newv(0) = vx: newv(1) = vy
    ret = False
    
    'addDonut2 vx, vy
    ddd = ent.Coordinates
    count = UBound(ddd)
    
    x1 = ddd(count - 1)
    y1 = ddd(count)
    
    For ii = 0 To count Step 2
    
        x2 = ddd(ii)
        y2 = ddd(ii + 1)
        
        f = getTan(x1, x2, y1, y2)
        f1 = getTan(x1, vx, y1, vy)
        f2 = getTan(vx, x2, vy, y2)
         
        fd = XYDistance(x1, y1, x2, y2)
        fd1 = XYDistance(x1, y1, vx, vy) + XYDistance(x2, y2, vx, vy)
        
        'addDonut x2, y2
        'addDonut x1, y1
        
        If Abs(fd - fd1) < PD_TOL Then
            
            'addDonut x2, y2
            'addDonut x1, y1
            
            
            newp = crossXY(vx, vy, x1, y1, x2, y2)
            
            'addDonut vx, vy
            
            newv(0) = newp(0)
            newv(1) = newp(1)
            addDonut vx, vy
            ent.addVertex ii / 2, newv
            ent.Update
            ret = True
        
        End If
        
        x1 = x2
        y1 = y2
        
    Next ii
    
    Debug.Print " "
    
    If ret = False Then
        newv(0) = 0
        newv(1) = 0
        Debug.Print "================NOT FOUND================"
    End If
    
    
    addVertex = newv
        
        
    
End Function

Function getTan(ByVal x1 As Double, ByVal x2 As Double, ByVal y1 As Double, ByVal y2 As Double) As Double
    
    Dim t As Double
    
    If x1 = x2 Then
    
        t = 1.79769313486232E+307
    Else
        t = (y2 - y1) / (x2 - x1)
    
    End If
    
    getTan = t

End Function






Function XYDistance(ByVal x1 As Double, ByVal y1 As Double, ByVal x2 As Double, ByVal y2 As Double) As Double
    Dim dblDist As Double
    Dim dblXSl As Double
    Dim dblYSl As Double

    Dim varErr As Variant
    On Error GoTo Err_Control

    dblXSl = (x1 - x2) ^ 2
    dblYSl = (y1 - y2) ^ 2
    dblDist = Sqr(dblXSl + dblYSl)

    XYDistance = dblDist

Exit_Here:
    Exit Function

Err_Control:

  Select Case Err.Number

  'Add additional Case selections here

    Case Else

    MsgBox Err.Description

    Err.Clear

    Resume Exit_Here

  End Select

End Function

Attribute VB_Name = "selector"

Const VK_ESCAPE = &H1B, VK_ENTER = &HD, VK_LBUTTON = &H1
Declare PtrSafe Function GetAsyncKeyState Lib "user32" (ByVal vKey As Long) As Integer


Function CheckKey(lngKey As Long) As Boolean
    If GetAsyncKeyState(lngKey) Then
        CheckKey = True
        Debug.Print "True"
        
    Else
        CheckKey = False
        Debug.Print "False"
    End If
End Function


Function selectArcObs() As AcadEntity()
    Dim UsersSelection As AcadSelectionSet
    Dim FilterType(0) As Integer
    Dim FilterData(0) As Variant
    Dim arcObjs() As AcadEntity
 
     With ThisDrawing
        On Error Resume Next
        
        .SelectionSets("CurrentSelection").Delete
        Set UsersSelection = .SelectionSets.add("CurrentSelection")
        
        FilterType(0) = 0
        FilterData(0) = "Arc"
        
        UsersSelection.SelectOnScreen FilterType, FilterData
        
        
        count = getEntitySize(UsersSelection, "AcDbArc")
        
        ReDim arcObjs(0 To count - 1) As AcadEntity
        
        For i = 0 To count
            Set arcObjs(i) = UsersSelection.Item(i)
        Next i
        
        
    End With
    
    selectArcObs = arcObjs

End Function



Function selectArcObj() As AcadEntity
    Dim UsersSelection As AcadSelectionSet
    Dim FilterType(0) As Integer
    Dim FilterData(0) As Variant
    Dim arcObjs As AcadEntity
    Dim count As Integer
 
     With ThisDrawing
        On Error Resume Next
        
        .SelectionSets("CurrentSelection").Delete
        Set UsersSelection = .SelectionSets.add("CurrentSelection")
        
        FilterType(0) = 0
        FilterData(0) = "Arc"
        
        UsersSelection.SelectOnScreen FilterType, FilterData
        
        
        count = getEntitySize(UsersSelection, "AcDbArc")
        
        For i = 0 To count
            Set arcObjs = UsersSelection.Item(i)
            Exit For
        Next i
        
        
    End With
    
    Set selectArcObj = arcObjs

End Function

 

Function selectPolyline()

    Dim newroad As AcadEntity
    Dim basePnt1 As Variant
        
    On Error GoTo Start
    
Start:
    ThisDrawing.Utility.getEntity newroad, basePnt1, "Get Object1: "
    
    
    Debug.Print ""
    
    

End Function


Function selectObjs() As AcadEntity()
    Dim UsersSelection As AcadSelectionSet
    Dim FilterType(0) As Integer
    Dim FilterData(0) As Variant
    Dim arcObjs() As AcadEntity
 
     With ThisDrawing
        On Error Resume Next
        
        .SelectionSets("CurrentSelection").Delete
        Set UsersSelection = .SelectionSets.add("CurrentSelection")
        
        UsersSelection.SelectOnScreen
        
        ReDim arcObjs(0 To UsersSelection.count - 1) As AcadEntity
        For i = 0 To UsersSelection.count
            Set arcObjs(i) = UsersSelection.Item(i)
        Next i
        
        
    End With
    
    selectObjs = arcObjs

End Function


Function selectEntity() As AcadEntity
    Dim UsersSelection As AcadSelectionSet
    Dim FilterType(0) As Integer
    Dim FilterData(0) As Variant
    Dim arcObjs() As AcadEntity
    Dim returnObj1 As AcadObject
    Dim basePnt1 As Variant
 
    ThisDrawing.Utility.getEntity returnObj1, basePnt1, "Get Object: "
    
    selectObj = returnObj1

End Function


Function selectSubEntity() As AcadEntity
    Dim UsersSelection As AcadSelectionSet
    Dim FilterType(0) As Integer
    Dim FilterData(0) As Variant
    Dim arcObjs() As AcadEntity
    Dim returnObj1 As AcadObject
    Dim basePnt1 As Variant
 
    ThisDrawing.Utility.GetSubEntity
    
    selectObj = returnObj1

End Function


Function selectlineObs() As AcadEntity()
    Dim UsersSelection As AcadSelectionSet
    Dim FilterType(0) As Integer
    Dim FilterData(0) As Variant
    Dim arcObjs() As AcadEntity
 
     With ThisDrawing
        On Error Resume Next
        
        .SelectionSets("CurrentSelection").Delete
        Set UsersSelection = .SelectionSets.add("CurrentSelection")
        
        FilterType(0) = 0
        FilterData(0) = "Line"
        
        UsersSelection.SelectOnScreen FilterType, FilterData
        
        
        count = getEntitySize(UsersSelection, "AcDbLine")
        
        ReDim arcObjs(0 To count - 1) As AcadEntity
        
        For i = 0 To count
            Set arcObjs(i) = UsersSelection.Item(i)
        Next i
        
        
    End With
    
    selectlineObs = arcObjs

End Function



Function selectPolylineObs() As AcadEntity()
    Dim UsersSelection As AcadSelectionSet
    Dim FilterType(0) As Integer
    Dim FilterData(0) As Variant
    Dim arcObjs() As AcadEntity
 
     With ThisDrawing
        On Error Resume Next
        
        .SelectionSets("CurrentSelection").Delete
        Set UsersSelection = .SelectionSets.add("CurrentSelection")
        
        FilterType(0) = 0
        FilterData(0) = "LWPolyline"
        
        UsersSelection.SelectOnScreen FilterType, FilterData
        
        
        count = getEntitySize(UsersSelection, "AcDbPolyline")
        
        ReDim arcObjs(0 To count - 1) As AcadEntity
        
        For i = 0 To count
            Set arcObjs(i) = UsersSelection.Item(i)
        Next i
        
        
    End With
    
    selectPolylineObs = arcObjs

End Function


Function selectObjs2() As AcadEntity()
    Dim UsersSelection As AcadSelectionSet
    Dim FilterType(0) As Integer
    Dim FilterData(0) As Variant
    Dim arcObjs() As AcadEntity
 
 
 
     With ThisDrawing
        On Error Resume Next
                
        
        .SelectionSets("CurrentSelection").Delete
        Set UsersSelection = .SelectionSets.add("CurrentSelection")
        
        UsersSelection.SelectOnScreen
        
        ReDim arcObjs(0 To UsersSelection.count - 1) As AcadEntity
        For i = 0 To UsersSelection.count
            Set arcObjs(i) = UsersSelection.Item(i)
        Next i
        
        
    End With
    
    
    selectObjs = arcObjs

End Function

Attribute VB_Name = "showdebug"



Function addDonut(ByVal x1 As Double, ByVal y1 As Double)

    
    Dim circleObj As AcadCircle
    Dim centerPoint(0 To 2) As Double
     
    If SHOW_CIRCLE = True Then
        centerPoint(0) = x1
        centerPoint(1) = y1
        
        Set circleObj = ThisDrawing.ModelSpace.AddCircle(centerPoint, 1)
        circleObj.Update
    End If

End Function

Function addDonut_2(ByVal x1 As Double, ByVal y1 As Double)

    Dim circleObj As AcadCircle
    Dim centerPoint(0 To 2) As Double
    
 
    If SHOW_CIRCLE = True Then
        centerPoint(0) = x1
        centerPoint(1) = y1
        
        Set circleObj = ThisDrawing.ModelSpace.AddCircle(centerPoint, 0.5)
        circleObj.Update
    End If
    

End Function

Function addDonut3(ByVal x1 As Double, ByVal y1 As Double)

    Dim circleObj As AcadCircle
    Dim centerPoint(0 To 2) As Double
    
    
    If SHOW_CIRCLE = True Then
        centerPoint(0) = x1
        centerPoint(1) = y1
        
        Set circleObj = ThisDrawing.ModelSpace.AddCircle(centerPoint, 0.5)
        circleObj.Update
    End If
    

End Function

Function addDonut5(ByVal x1 As Double, ByVal y1 As Double)

    Dim circleObj As AcadCircle
    Dim centerPoint(0 To 2) As Double
    
 
    'If SHOW_CIRCLE = True Then
        centerPoint(0) = x1
        centerPoint(1) = y1
        
        Set circleObj = ThisDrawing.ModelSpace.AddCircle(centerPoint, 0.5)
        circleObj.Update
    'End If
    

End Function


Function addDonutR(ByVal x1 As Double, ByVal y1 As Double)

    Dim circleObj As AcadCircle
    Dim centerPoint(0 To 2) As Double
    
 
    If SHOW_CIRCLE = True Then
        centerPoint(0) = x1
        centerPoint(1) = y1
        
        Set circleObj = ThisDrawing.ModelSpace.AddCircle(centerPoint, 0.8)
        circleObj.color = acRed
        circleObj.Update
    End If
    

End Function


Function addDonutY(ByVal x1 As Double, ByVal y1 As Double)

    Dim circleObj As AcadCircle
    Dim centerPoint(0 To 2) As Double
    
 
    If SHOW_CIRCLE = True Then
        centerPoint(0) = x1
        centerPoint(1) = y1
        
        Set circleObj = ThisDrawing.ModelSpace.AddCircle(centerPoint, 0.7)
        circleObj.color = acYellow
        circleObj.Update
    End If
    

End Function



Function addDonutB(ByVal x1 As Double, ByVal y1 As Double)

    Dim circleObj As AcadCircle
    Dim centerPoint(0 To 2) As Double
    
 
    If SHOW_CIRCLE = True Then
        centerPoint(0) = x1
        centerPoint(1) = y1
        
        Set circleObj = ThisDrawing.ModelSpace.AddCircle(centerPoint, 0.6)
        circleObj.color = acBlue
        circleObj.Update
    End If
    

End Function



Function addDonutG(ByVal x1 As Double, ByVal y1 As Double)

    Dim circleObj As AcadCircle
    Dim centerPoint(0 To 2) As Double
    
 
    If SHOW_CIRCLE = True Then
        centerPoint(0) = x1
        centerPoint(1) = y1
        
        Set circleObj = ThisDrawing.ModelSpace.AddCircle(centerPoint, 1)
        circleObj.color = acGreen
        circleObj.Update
    End If
    

End Function


Function addLine(pts() As Double) As AcadEntity

    Dim ent As AcadEntity
    

    Set ent = ThisDrawing.ModelSpace.AddLightWeightPolyline(pts)

    Set addLine = ent

End Function

Attribute VB_Name = "topology"
Function getFarPoint1(list() As clsPoint, pt As clsPoint) As clsPoint

    Dim p As clsPoint
    Dim dd As Double
    Dim max As Double
    Dim idx As Integer
    
    max = 0
    
    For i = 0 To UBound(list)
    
        p = list(0)
        dd = pt.distance(p)
        
        If dd > max Then
            max = dd
            idx = i
            
        End If
        
    Next


    getFarPoint1 = list(idx)


End Function

Function getFarPoint2(list As Variant, pt As clsPoint) As clsPoint

    Dim p As New clsPoint
    Dim dd As Double
    Dim idx As Integer
    Dim x As Double
    Dim y As Double
    
    max = 0
    
     
    
    For i = 0 To UBound(list) Step 3
    
        x = list(0)
        y = list(1)
    
        p.initXy list(i), list(i + 1) 'x, y
        
        
        dd = pt.distance(p)
        
        If dd > max Then
            max = dd
            idx = i
            
        End If
        
    Next

    p.initXy list(idx), list(idx + 1)


    Set getFarPoint2 = p


End Function



Function getNearPoint2(list As Variant, pt As clsPoint) As clsPoint

    Dim p As New clsPoint
    Dim dd As Double
    Dim idx As Integer
    Dim x As Double
    Dim y As Double
    
    Min = 99999999
    
    For i = 0 To UBound(list) Step 3
    
        x = list(0)
        y = list(1)
    
        p.initXy list(i), list(i + 1) 'x, y
        
        dd = pt.distance(p)
        
        If dd < Min Then
            Min = dd
            idx = i
            
        End If
        
    Next

    p.initXy list(idx), list(idx + 1)


    Set getNearPoint2 = p


End Function


Function getLineByEntity(ent As AcadEntity, ByVal vx As Double, ByVal vy As Double) As AcadLine

    Dim newv(0 To 1) As Double
    Dim ddd() As Double
    Dim count As Integer
    Dim distance As Double

    Dim ret As Boolean
    Dim newp() As Double
    Dim line As AcadLine
    
    newv(0) = vx: newv(1) = vy
    ret = False
    
    addDonutR vx, vy
    ddd = ent.Coordinates
    count = UBound(ddd)
    
    x1 = ddd(count - 1)
    y1 = ddd(count)
    
    For ii = 0 To count Step 2
    
        x2 = ddd(ii)
        y2 = ddd(ii + 1)
        
        f = getTan(x1, x2, y1, y2)
        f1 = getTan(x1, vx, y1, vy)
        f2 = getTan(vx, x2, vy, y2)
         
        fd = XYDistance(x1, y1, x2, y2)
        fd1 = XYDistance(x1, y1, vx, vy) + XYDistance(x2, y2, vx, vy)
        
        If Abs(fd - fd1) < PD_TOL Then
            
            newp = crossXY(vx, vy, x1, y1, x2, y2)
            
            
            Dim sp(0 To 2) As Double
            Dim ep(0 To 2) As Double
            
            
            sp(0) = x1
            sp(1) = y1
            ep(0) = x2
            ep(1) = y2
            
            Set line = ThisDrawing.ModelSpace.addLine(sp, ep)
      
            
            addDonutY vx, vy
            
            Exit For
        
        End If
        
        x1 = x2
        y1 = y2
        
    Next ii
    
    Debug.Print " "
    
    If ret = False Then
        newv(0) = 0
        newv(1) = 0
    
    End If
        
   
    
    
    Set getLineByEntity = line
        
        
    
End Function


Function searchCrossVertext(src As AcadEntity, dst As AcadEntity) As Variant

    Dim size As Integer
    
    searchCrossVertext = src.IntersectWith(dst, acExtendNone)   'find vertex
    
End Function

Sub topologyTest()

    Dim p1 As New clsPoint
    Dim p2 As New clsPoint
    Dim distance As Double
    
    p1.initXy 0, 0
    p2.initXy 1, 1
    
    
    distance = p1.distance(p2)
    
    

End Sub
